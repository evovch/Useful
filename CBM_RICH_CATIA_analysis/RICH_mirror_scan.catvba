Attribute VB_Name = "Module1"
Option Explicit

Const PI = 3.14159265358979

Dim prt As Part
Dim hshpFac As HybridShapeFactory
Dim gsGenerated1 As HybridBody
Dim gsGenerated2 As HybridBody
Dim gsGenerated3 As HybridBody
Dim gsGenerated4 As HybridBody
Dim gsGenerated5 As HybridBody
Dim gsGenerated6 As HybridBody

Dim InteractionPoint As HybridShape
Dim mirrSurf As HybridShape
Dim cameraSurf As HybridShape

Sub CATMain()

    Dim actDoc As Document
    Dim prodDoc As ProductDocument
    Dim prod As Product
    Dim childProd As Product
    Dim prtDoc As PartDocument
    Dim hbds As HybridBodies
    Dim hshps As HybridShapes
    Dim gsConstruct As HybridBody
    Dim constrHshps As HybridShapes
    
    Set actDoc = CATIA.ActiveDocument
    
    If (TypeName(actDoc) = "ProductDocument") Then
        Set prodDoc = actDoc
        Set prod = prodDoc.Product
    End If
    
    Set childProd = prod.Products.GetItem("Part1.1")
    If (childProd Is Nothing) Then
        MsgBox "Could not find 'Part1.1' subproduct. Aborting."
        End
    Else
        'MsgBox "Found Part1.1 subproduct. OK."
    End If
    
    Set prtDoc = childProd.ReferenceProduct.Parent
    Set prt = prtDoc.Part
    Set hshpFac = prt.HybridShapeFactory
    Set hbds = prt.HybridBodies
    Set gsConstruct = hbds.GetItem("Construct")
    Set gsGenerated1 = hbds.GetItem("Generated.1")
    Set gsGenerated2 = hbds.GetItem("Generated.2")
    Set gsGenerated3 = hbds.GetItem("Generated.3")
    Set gsGenerated4 = hbds.GetItem("Generated.4")
    Set gsGenerated5 = hbds.GetItem("Generated.5")
    Set gsGenerated6 = hbds.GetItem("Generated.6")
    
    If (gsConstruct Is Nothing) Then
        MsgBox "Could not find geometrical set 'Construct'. Aborting."
        End
    Else
        'MsgBox "Found geometrical set 'Construct'. OK."
    End If
        
    If (gsGenerated1 Is Nothing) Then
        MsgBox "Could not find geometrical set 'Generated.1'. Aborting."
        End
    Else
        'MsgBox "Found geometrical set 'Generated.1'. OK."
    End If
        
    If (gsGenerated2 Is Nothing) Then
        MsgBox "Could not find geometrical set 'Generated.2'. Aborting."
        End
    Else
        'MsgBox "Found geometrical set 'Generated.2'. OK."
    End If

    If (gsGenerated3 Is Nothing) Then
        MsgBox "Could not find geometrical set 'Generated.3'. Aborting."
        End
    Else
        'MsgBox "Found geometrical set 'Generated.3'. OK."
    End If
        
    If (gsGenerated4 Is Nothing) Then
        MsgBox "Could not find geometrical set 'Generated.4'. Aborting."
        End
    Else
        'MsgBox "Found geometrical set 'Generated.4'. OK."
    End If

    If (gsGenerated5 Is Nothing) Then
        MsgBox "Could not find geometrical set 'Generated.5'. Aborting."
        End
    Else
        'MsgBox "Found geometrical set 'Generated.5'. OK."
    End If
        
    If (gsGenerated6 Is Nothing) Then
        MsgBox "Could not find geometrical set 'Generated.6'. Aborting."
        End
    Else
        'MsgBox "Found geometrical set 'Generated.6'. OK."
    End If

    Set constrHshps = gsConstruct.HybridShapes
    
    Set InteractionPoint = constrHshps.GetItem("IP")

    If (InteractionPoint Is Nothing) Then
        MsgBox "Could not find 'IP' in GS 'Construct'. Aborting."
        End
    Else
        'MsgBox "Found 'IP' in GS 'Construct'. OK."
    End If
    
    Set mirrSurf = constrHshps.GetItem("Mirror_surface")

    If (mirrSurf Is Nothing) Then
        MsgBox "Could not find 'Mirror_surface' in GS 'Construct'. Aborting."
        End
    Else
        'MsgBox "Found 'Mirror_surface' in GS 'Construct'. OK."
    End If
    
    Set cameraSurf = constrHshps.GetItem("Camera_surface")

    If (cameraSurf Is Nothing) Then
        MsgBox "Could not find 'Camera_surface' in GS 'Construct'. Aborting."
        End
    Else
        'MsgBox "Found 'Camera_surface' in GS 'Construct'. OK."
    End If
    
    Call GenerateGridPointsAndLines1
    Call GenerateIntersections1
    Call GenerateNormals1
    Call GenerateReflections1
    Call GenerateIntersections2

    'UserForm1.Show vbModeless
    
    MsgBox "Done!"

End Sub

Public Sub GenerateGridPointsAndLines1()

    Dim lineLength As Double
    lineLength = 5000#

    ' Number of steps
    Dim nPhi As Integer
    Dim nTheta As Integer
    ' Start values
    Dim startPhi As Double
    Dim startTheta As Double
    ' End values
    Dim endPhi As Double
    Dim endTheta As Double
    ' Step
    Dim stepPhi As Double
    Dim stepTheta As Double
    ' Current index and value
    Dim iPhi As Integer
    Dim iTheta As Integer
    Dim curPhi As Double
    Dim curTheta As Double
    Dim scalingK As Double

    Dim curX As Double
    Dim curY As Double
    Dim curZ As Double

    Dim newPoint As HybridShape
    Dim newLine As HybridShape

    startPhi = 0#
    startTheta = 0#
    endPhi = 90#
    endTheta = 25#
    scalingK = 1.5
    nPhi = 10
    nTheta = 10
    stepPhi = (endPhi - startPhi) / nPhi
    stepTheta = (endTheta - startTheta) / nTheta
    
    For iPhi = 0 To nPhi
        
        'stepTheta = ((endTheta - startTheta) / nTheta) * (1# + 0.5 * (endPhi - curPhi) / endPhi)
        
        For iTheta = 0 To nTheta
            curPhi = (startPhi + iPhi * stepPhi)
            
            curTheta = (startTheta + iTheta * stepTheta)
            
'            UserForm1.ListBox1.AddItem "iPhi=" + Trim(Str(iPhi)) + vbTab + _
'                                       "iTheta=" + Trim(Str(iTheta)) + vbTab + _
'                                       "curPhi=" + Trim(Str(curPhi)) + vbTab + _
'                                       "stepTheta=" + Trim(Str(stepTheta)) + vbTab + _
'                                       "curTheta=" + Trim(Str(curTheta))
            
            ' Horizontal scaling
            curX = lineLength * Sin(curTheta * PI / 180#) * Cos(curPhi * PI / 180#) * 1.5
            curY = lineLength * Sin(curTheta * PI / 180#) * Sin(curPhi * PI / 180#)
            curZ = lineLength * Cos(curTheta * PI / 180#)

'            UserForm1.ListBox1.AddItem "phi=" + Trim(Str(curPhi)) + vbTab + _
'                                       "theta=" + Trim(Str(curTheta)) + vbTab + _
'                                       "x=" + Trim(Str(curX)) + vbTab + _
'                                       "y=" + Trim(Str(curY)) + vbTab + _
'                                       "z=" + Trim(Str(curZ))

            Set newPoint = hshpFac.AddNewPointCoord(curX, curY, curZ)
            newPoint.Name = "GridPoint." + Trim(Str(curPhi)) + "." + Trim(Str(curTheta))
            gsGenerated1.AppendHybridShape newPoint

            Set newLine = hshpFac.AddNewLinePtPt(InteractionPoint, newPoint)
            newLine.Name = "GridLine." + Trim(Str(curPhi)) + "." + Trim(Str(curTheta))
            gsGenerated2.AppendHybridShape newLine

        Next iTheta
    Next iPhi

    prt.Update
    
End Sub

Public Sub GenerateIntersections1()

    Dim iLine As Integer
    Dim lines As HybridShapes
    Dim curLine As HybridShape
    Dim intersectHshape As HybridShape
    Dim refLine As Reference
    Dim refMirrSurf As Reference

    Set refMirrSurf = prt.CreateReferenceFromObject(mirrSurf)

    Set lines = gsGenerated2.HybridShapes
    For iLine = 1 To lines.Count
        Set curLine = lines.Item(iLine)
        Set refLine = prt.CreateReferenceFromObject(curLine)
        Set intersectHshape = hshpFac.AddNewIntersection(refLine, refMirrSurf)
        intersectHshape.Name = "Inter." + Trim(Str(iLine))
        gsGenerated3.AppendHybridShape intersectHshape
    Next iLine

    prt.Update

End Sub

Public Sub GenerateNormals1()

    Dim iInter As Integer
    Dim inters As HybridShapes
    Dim curInter As HybridShape
    Dim normalHshape As HybridShape
    Dim refInter As Reference
    Dim refMirrSurf As Reference

    Set refMirrSurf = prt.CreateReferenceFromObject(mirrSurf)

    Set inters = gsGenerated3.HybridShapes
    For iInter = 1 To inters.Count
        Set curInter = inters.Item(iInter)
        Set refInter = prt.CreateReferenceFromObject(curInter)
        Set normalHshape = hshpFac.AddNewLineNormal(refMirrSurf, refInter, 0#, 3000#, True)
        normalHshape.Name = "Norm." + Trim(Str(iInter))
        gsGenerated4.AppendHybridShape normalHshape
    Next iInter

    prt.Update

End Sub

Public Sub GenerateReflections1()

    Dim iNorm As Integer
    
    Dim lines As HybridShapes
    Dim norms As HybridShapes
    Dim curLine As HybridShape
    Dim curNorm As HybridShape
    Dim refLine As Reference
    Dim refNorm As Reference
    
    Dim reflHshape As HybridShape
    
    Set lines = gsGenerated2.HybridShapes
    Set norms = gsGenerated4.HybridShapes
    
    For iNorm = 1 To norms.Count
    
        Set curLine = lines.Item(iNorm)
        Set curNorm = norms.Item(iNorm)
        Set refLine = prt.CreateReferenceFromObject(curLine)
        Set refNorm = prt.CreateReferenceFromObject(curNorm)
        
        Set reflHshape = hshpFac.AddNewRotate(refLine, refNorm, 180#)
        reflHshape.Name = "Refl." + Trim(Str(iNorm))
        gsGenerated5.AppendHybridShape reflHshape
    Next iNorm

    prt.Update

End Sub

Public Sub GenerateIntersections2()

    Dim iRefl As Integer
    Dim refls As HybridShapes
    Dim curRefl As HybridShape
    Dim intersectHshape As HybridShape
    Dim refRefl As Reference
    Dim refCameraSurf As Reference

    Set refCameraSurf = prt.CreateReferenceFromObject(cameraSurf)

    Set refls = gsGenerated5.HybridShapes
    For iRefl = 1 To refls.Count
        Set curRefl = refls.Item(iRefl)
        Set refRefl = prt.CreateReferenceFromObject(curRefl)
        Set intersectHshape = hshpFac.AddNewIntersection(refRefl, refCameraSurf)
        intersectHshape.Name = "Inter2." + Trim(Str(iRefl))
        gsGenerated6.AppendHybridShape intersectHshape
    Next iRefl

    prt.Update

End Sub
