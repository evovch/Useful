Attribute VB_Name = "Matrix"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' Matrix class

' First index is column index, second - row index

' | 0,0 | 1,0 | 2,0 | 3,0 |
' | 0,1 | 1,1 | 2,1 | 3,1 |
' | 0,2 | 1,2 | 2,2 | 3,2 |
' | 0,3 | 1,3 | 2,3 | 3,3 |

Option Explicit

Const PI = 3.14159265358979

Const TOLERANCE = 12

Private mData(15) As Double

' Reconstructed rotation angles
Public mRecoAlpha As Double ' around Z
Public mRecoBeta As Double ' around Y
Public mRecoGamma As Double ' around X

' Reconstructed translation coordinates
Public mRecoShiftX As Double
Public mRecoShiftY As Double
Public mRecoShiftZ As Double

' Constructor
Public Sub Class_Initialize()
    Call InitE
End Sub

' Correct but not used
'Public Function Clone() As Matrix
'    Dim theClone As New Matrix
'    Dim iCol As Integer
'    Dim jRow As Integer
'    For jRow = 0 To 3
'        For iCol = 0 To 3
'            theClone.SetData iCol, jRow, Me.GetData(iCol, jRow)
'        Next iCol
'    Next jRow
'    Set Clone = theClone
'End Function

' Copy data from the 'source' into this matrix
Public Sub Copy(source As Matrix)
    Dim iCol As Integer
    Dim jRow As Integer
    For jRow = 0 To 3
        For iCol = 0 To 3
            Me.SetData iCol, jRow, source.GetData(iCol, jRow)
        Next iCol
    Next jRow
End Sub

' Init with unity diagonal matrix E
Public Sub InitE()
    Dim iCol As Integer
    Dim jRow As Integer
    For jRow = 0 To 3
        For iCol = 0 To 3
            If iCol = jRow Then
                Me.SetData iCol, jRow, 1#
            Else
                Me.SetData iCol, jRow, 0#
            End If
        Next iCol
    Next jRow
End Sub

' Accessor
Public Function GetData(iCol As Integer, jRow As Integer) As Double
    GetData = mData(iCol * 4 + jRow)
End Function

' Modifier
Public Sub SetData(iCol As Integer, jRow As Integer, newVal As Double)
    mData(iCol * 4 + jRow) = newVal
End Sub

Public Sub Init4x4(p_a11 As Double, p_a12 As Double, p_a13 As Double, p_a14 As Double, _
                   p_a21 As Double, p_a22 As Double, p_a23 As Double, p_a24 As Double, _
                   p_a31 As Double, p_a32 As Double, p_a33 As Double, p_a34 As Double, _
                   p_a41 As Double, p_a42 As Double, p_a43 As Double, p_a44 As Double)
                   
    mData(0, 0) = p_a11
    mData(0, 1) = p_a21
    mData(0, 2) = p_a31
    mData(0, 3) = p_a41
    
    mData(1, 0) = p_a12
    mData(1, 1) = p_a22
    mData(1, 2) = p_a32
    mData(1, 3) = p_a42
    
    mData(2, 0) = p_a13
    mData(2, 1) = p_a23
    mData(2, 2) = p_a33
    mData(2, 3) = p_a43
    
    mData(3, 0) = p_a14
    mData(3, 1) = p_a24
    mData(3, 2) = p_a34
    mData(3, 3) = p_a44
    
End Sub

Public Sub Dump(preMessage As String)
    ' Tolerance in this round function calls does not matter -
    ' it is just for nice number printing
    Dim tol As Integer
    tol = 12
    Dim message As String
    message = preMessage + vbNewLine + _
           "| " + Str(Round(Me.GetData(0, 0), tol)) + vbTab + _
           "| " + Str(Round(Me.GetData(1, 0), tol)) + vbTab + _
           "| " + Str(Round(Me.GetData(2, 0), tol)) + vbTab + _
           "| " + Str(Round(Me.GetData(3, 0), tol)) + vbNewLine + _
           "| " + Str(Round(Me.GetData(0, 1), tol)) + vbTab + _
           "| " + Str(Round(Me.GetData(1, 1), tol)) + vbTab + _
           "| " + Str(Round(Me.GetData(2, 1), tol)) + vbTab + _
           "| " + Str(Round(Me.GetData(3, 1), tol)) + vbNewLine + _
           "| " + Str(Round(Me.GetData(0, 2), tol)) + vbTab + _
           "| " + Str(Round(Me.GetData(1, 2), tol)) + vbTab + _
           "| " + Str(Round(Me.GetData(2, 2), tol)) + vbTab + _
           "| " + Str(Round(Me.GetData(3, 2), tol)) + vbNewLine + _
           "| " + Str(Round(Me.GetData(0, 3), tol)) + vbTab + _
           "| " + Str(Round(Me.GetData(1, 3), tol)) + vbTab + _
           "| " + Str(Round(Me.GetData(2, 3), tol)) + vbTab + _
           "| " + Str(Round(Me.GetData(3, 3), tol))
    Write #1, message
    'Write #1, vbNewLine
    'MsgBox message
End Sub

Public Sub InitTXYZ(rotZ As Double, _
                    rotY As Double, _
                    rotX As Double, _
                    trX As Double, _
                    trY As Double, _
                    trZ As Double)

    Dim Mz As New Matrix ' rotation around Z
    Dim My As New Matrix ' rotation around Y
    Dim Mx As New Matrix ' rotation around X
    Dim Mtr As New Matrix ' translation
    Dim Mtxyz As New Matrix ' all four together

    Mz.InitZrot -rotZ
    My.InitYrot -rotY
    Mx.InitXrot -rotX
    Mtr.InitXYZposRow trX, trY, trZ
    'Mz.Dump "Mz (rot. around Z) alpha=" + Trim(Str(rotZ))
    'My.Dump "My (rot. around Y) beta=" + Trim(Str(rotY))
    'Mx.Dump "Mx (rot. around X) gamma=" + Trim(Str(rotX))
    'Mtr.Dump "Mtr (tr. along X, Y, and Z) trX=" + Trim(Str(trX)) + _
                                        " trY=" + Trim(Str(trY)) + _
                                        " trZ=" + Trim(Str(trZ))

    Mtxyz.InitE
    'Mtxyz.Dump "Mtxyz (E - initial state)"
    Mtxyz.Multiply Mz
    'Mtxyz.Dump "Mtxyz (E*Mz)"
    Mtxyz.Multiply My
    'Mtxyz.Dump "Mtxyz (E*Mz*My)"
    Mtxyz.Multiply Mx
    'Mtxyz.Dump "Mtxyz (E*Mz*My*Mx)"
    Mtxyz.Multiply Mtr
    Mtxyz.Dump "Mtxyz (E*Mz*My*Mx*Mtr)"

    Me.Copy Mtxyz

End Sub

Public Sub InitXrot(gammaDeg As Double)

    Dim gamma As Double
    gamma = gammaDeg * PI / 180#

    Me.SetData 0, 0, 1#
    Me.SetData 0, 1, 0#
    Me.SetData 0, 2, 0#
    Me.SetData 0, 3, 0#
    
    Me.SetData 1, 0, 0#
    Me.SetData 1, 1, Cos(gamma)
    Me.SetData 1, 2, Sin(gamma)
    Me.SetData 1, 3, 0#
    
    Me.SetData 2, 0, 0#
    Me.SetData 2, 1, -Sin(gamma)
    Me.SetData 2, 2, Cos(gamma)
    Me.SetData 2, 3, 0#

    Me.SetData 3, 0, 0#
    Me.SetData 3, 1, 0#
    Me.SetData 3, 2, 0#
    Me.SetData 3, 3, 1#
    
End Sub

Public Sub InitYrot(betaDeg As Double)

    Dim beta As Double
    beta = betaDeg * PI / 180#

    Me.SetData 0, 0, Cos(beta)
    Me.SetData 0, 1, 0#
    Me.SetData 0, 2, -Sin(beta)
    Me.SetData 0, 3, 0#
    
    Me.SetData 1, 0, 0#
    Me.SetData 1, 1, 1#
    Me.SetData 1, 2, 0#
    Me.SetData 1, 3, 0#
    
    Me.SetData 2, 0, Sin(beta)
    Me.SetData 2, 1, 0#
    Me.SetData 2, 2, Cos(beta)
    Me.SetData 2, 3, 0#

    Me.SetData 3, 0, 0#
    Me.SetData 3, 1, 0#
    Me.SetData 3, 2, 0#
    Me.SetData 3, 3, 1#
    
End Sub

Public Sub InitZrot(alphaDeg As Double)

    Dim alpha As Double
    alpha = alphaDeg * PI / 180#

    Me.SetData 0, 0, Cos(alpha)
    Me.SetData 0, 1, Sin(alpha)
    Me.SetData 0, 2, 0#
    Me.SetData 0, 3, 0#
    
    Me.SetData 1, 0, -Sin(alpha)
    Me.SetData 1, 1, Cos(alpha)
    Me.SetData 1, 2, 0#
    Me.SetData 1, 3, 0#
    
    Me.SetData 2, 0, 0#
    Me.SetData 2, 1, 0#
    Me.SetData 2, 2, 1#
    Me.SetData 2, 3, 0#
    
    Me.SetData 3, 0, 0#
    Me.SetData 3, 1, 0#
    Me.SetData 3, 2, 0#
    Me.SetData 3, 3, 1#
    
End Sub

Public Sub InitXYZposRow(x As Double, y As Double, z As Double)
    Me.InitE
    Me.SetData 0, 3, x
    Me.SetData 1, 3, y
    Me.SetData 2, 3, z
End Sub

' Correct but not used
'Public Sub InitXYZposCol(x As Double, y As Double, z As Double)
'    Me.InitE
'    Me.SetData 3, 0, x
'    Me.SetData 3, 1, y
'    Me.SetData 3, 2, z
'End Sub

' Multiply currect matrix by some right operand
Public Sub Multiply(right_op As Matrix)
    Dim iCol As Integer
    Dim jRow As Integer
    Dim K As Integer
    Dim sum As Double
    Dim left_op As New Matrix
    'Set left_op = Me.Clone
    left_op.Copy Me
    For iCol = 0 To 3
        For jRow = 0 To 3
            sum = 0
            For K = 0 To 3
                sum = sum + left_op.GetData(K, jRow) * right_op.GetData(iCol, K)
            Next K
            Me.SetData iCol, jRow, sum
        Next jRow
    Next iCol
End Sub

Public Sub Transpose()
    Dim iCol As Integer
    Dim jRow As Integer
    Dim tmp As Double
    For iCol = 0 To 3
        For jRow = iCol + 1 To 3
            tmp = Me.GetData(iCol, jRow)
            Me.SetData iCol, jRow, Me.GetData(jRow, iCol)
            Me.SetData jRow, iCol, tmp
        Next jRow
    Next iCol
End Sub

Public Function Det() As Double
    
    Dim minor As New Matrix3by3
    Dim minorDet As Double
    
    Dim sum As Double
    Dim sign As Boolean ' true+ false-
    
    sum = 0#
    sign = True
    
    Dim iCol As Integer
    For iCol = 0 To 3
        minor.Construct Me, iCol, 0
        minorDet = minor.Det
        If (sign = True) Then
            sum = sum + Me.GetData(iCol, 0) * minorDet
            sign = False
        Else
            sum = sum - Me.GetData(iCol, 0) * minorDet
            sign = True
        End If
    Next iCol

    Det = sum

End Function

Public Function Inverse() As Matrix

    Dim meDet As Double
    meDet = Me.Det

    Dim resultM As New Matrix

    Dim minor As New Matrix3by3
    Dim minorDet As Double
    
    Dim iCol As Integer
    Dim jRow As Integer
    
    For jRow = 0 To 3
        For iCol = 0 To 3
        
            minor.Construct Me, iCol, jRow
            minorDet = minor.Det
            resultM.SetData jRow, iCol, minorDet * (-1) ^ (iCol + jRow) * (1# / meDet)
            
            'Write #1, "iCol=" + Trim(Str(iCol)) + " jRow=" + Trim(Str(jRow)) + "   det: " + Trim(Str(minorDet))
            'Write #1, "iCol=" + Trim(Str(iCol)) + " jRow=" + Trim(Str(jRow)) + _
            '          " value: " + Trim(Str(minorDet * (-1) ^ (iCol + jRow)))
            'minor.Dump "iCol=" + Trim(Str(iCol)) + " jRow=" + Trim(Str(jRow)) + " minor: "

        Next iCol
    Next jRow
    
    Set Inverse = resultM

    ' Perform check
    'Dim multRes As New Matrix
    'multRes.Copy resultM
    'multRes.Multiply Me
    'multRes.Dump "This should be E!"

End Function

Public Sub InitBy4Points(pointXdir, pointYdir, pointZdir, pointOrigin)

    Dim coordsVarXdir(2) As Variant
    Dim coordsVarYdir(2) As Variant
    Dim coordsVarZdir(2) As Variant
    Dim coordsVarOrigin(2) As Variant
    
    Dim coordsDouble(11) As Double

    pointXdir.GetCoordinates coordsVarXdir
    pointYdir.GetCoordinates coordsVarYdir
    pointZdir.GetCoordinates coordsVarZdir
    pointOrigin.GetCoordinates coordsVarOrigin

    coordsDouble(0) = coordsVarXdir(0) ' Xdir point - coordinate x
    coordsDouble(1) = coordsVarXdir(1) ' Xdir point - coordinate y
    coordsDouble(2) = coordsVarXdir(2) ' Xdir point - coordinate z
    coordsDouble(3) = coordsVarYdir(0) ' Ydir point - coordinate x
    coordsDouble(4) = coordsVarYdir(1) ' Ydir point - coordinate y
    coordsDouble(5) = coordsVarYdir(2) ' Ydir point - coordinate z
    coordsDouble(6) = coordsVarZdir(0) ' Zdir point - coordinate x
    coordsDouble(7) = coordsVarZdir(1) ' Zdir point - coordinate y
    coordsDouble(8) = coordsVarZdir(2) ' Zdir point - coordinate z
    coordsDouble(9) = coordsVarOrigin(0) ' origin - coordinate x
    coordsDouble(10) = coordsVarOrigin(1) ' origin - coordinate y
    coordsDouble(11) = coordsVarOrigin(2) ' origin - coordinate z

    Me.InitE
    Me.SetData 0, 0, coordsDouble(0) - coordsDouble(9)  ' Here's the magic
    Me.SetData 1, 0, coordsDouble(1) - coordsDouble(10) ' Here's the magic
    Me.SetData 2, 0, coordsDouble(2) - coordsDouble(11) ' Here's the magic
    Me.SetData 0, 1, coordsDouble(3) - coordsDouble(9)  ' Here's the magic
    Me.SetData 1, 1, coordsDouble(4) - coordsDouble(10) ' Here's the magic
    Me.SetData 2, 1, coordsDouble(5) - coordsDouble(11) ' Here's the magic
    Me.SetData 0, 2, coordsDouble(6) - coordsDouble(9)  ' Here's the magic
    Me.SetData 1, 2, coordsDouble(7) - coordsDouble(10) ' Here's the magic
    Me.SetData 2, 2, coordsDouble(8) - coordsDouble(11) ' Here's the magic
    Me.SetData 0, 3, coordsDouble(9)
    Me.SetData 1, 3, coordsDouble(10)
    Me.SetData 2, 3, coordsDouble(11)
    
End Sub

Public Sub CreateGeometry(fact As HybridShapeFactory, geomSet As HybridBody, suffix As String)

    ' Create new points
    Dim pCS0(3) As HybridShapePointCoord
    Set pCS0(0) = fact.AddNewPointCoord(Me.GetData(0, 3) + Me.GetData(0, 0), _
                                        Me.GetData(1, 3) + Me.GetData(1, 0), _
                                        Me.GetData(2, 3) + Me.GetData(2, 0))
    Set pCS0(1) = fact.AddNewPointCoord(Me.GetData(0, 3) + Me.GetData(0, 1), _
                                        Me.GetData(1, 3) + Me.GetData(1, 1), _
                                        Me.GetData(2, 3) + Me.GetData(2, 1))
    Set pCS0(2) = fact.AddNewPointCoord(Me.GetData(0, 3) + Me.GetData(0, 2), _
                                        Me.GetData(1, 3) + Me.GetData(1, 2), _
                                        Me.GetData(2, 3) + Me.GetData(2, 2))
    Set pCS0(3) = fact.AddNewPointCoord(Me.GetData(0, 3), Me.GetData(1, 3), Me.GetData(2, 3))
    pCS0(0).Name = "Point." + suffix + ".recoX"
    pCS0(1).Name = "Point." + suffix + ".recoY"
    pCS0(2).Name = "Point." + suffix + ".recoZ"
    pCS0(3).Name = "Point." + suffix + ".recoO"
    
    geomSet.AppendHybridShape pCS0(0)
    geomSet.AppendHybridShape pCS0(1)
    geomSet.AppendHybridShape pCS0(2)
    geomSet.AppendHybridShape pCS0(3)
    
    ' Create new lines
    Dim lCS0(2) As HybridShapeLinePtPt
    Set lCS0(0) = fact.AddNewLinePtPt(pCS0(3), pCS0(0))
    Set lCS0(1) = fact.AddNewLinePtPt(pCS0(3), pCS0(1))
    Set lCS0(2) = fact.AddNewLinePtPt(pCS0(3), pCS0(2))
    lCS0(0).Name = "Line." + suffix + ".X"
    lCS0(1).Name = "Line." + suffix + ".Y"
    lCS0(2).Name = "Line." + suffix + ".Z"
    
    geomSet.AppendHybridShape lCS0(0)
    geomSet.AppendHybridShape lCS0(1)
    geomSet.AppendHybridShape lCS0(2)

End Sub

Public Sub ExtractAnglesAndCoordinates()

    Dim A As Double
    Dim B As Double
    Dim C As Double
    Dim D As Double
    Dim F As Double
    Dim G As Double
    Dim J As Double
    Dim H As Double
    Dim K As Double
    Dim L As Double
    Dim M As Double
    
    If (Round(Me.GetData(0, 2), TOLERANCE) = 0#) Then
        ' sin(beta) = 0
        ' this is the case when either beta = 0
        '                           or beta = 180
        '                           or beta =-180
    
        mRecoBeta = 0#
        mRecoAlpha = myAsin(-Me.GetData(0, 1), Me.GetData(0, 0)) * 180# / PI ' TODO actually this is true only for beta=0
        mRecoGamma = myAsin(-Me.GetData(1, 2), Me.GetData(2, 2)) * 180# / PI ' TODO actually this is true only for beta=0
        
        mRecoShiftX = Me.GetData(0, 3)
        mRecoShiftY = Me.GetData(1, 3)
        mRecoShiftZ = Me.GetData(2, 3)

        Write #1, "reco alpha = " + Trim(Str(mRecoAlpha))
        Write #1, "reco beta  = " + Trim(Str(mRecoBeta))
        Write #1, "reco gamma = " + Trim(Str(mRecoGamma))
        
        Write #2, "reco alpha = " + Trim(Str(mRecoAlpha))
        Write #2, "reco beta  = " + Trim(Str(mRecoBeta))
        Write #2, "reco gamma = " + Trim(Str(mRecoGamma))

        Exit Sub
    End If
    
    If (Round(Me.GetData(0, 2), TOLERANCE) = 1#) Then
        ' sin(beta) = 1
        ' this is the case when beta = 90

        ' G = sin(alpha+gamma)
        G = Me.GetData(1, 0)
        ' J = cos(alpha+gamma)
        J = Me.GetData(1, 1)
        
        mRecoBeta = 90#
        mRecoAlpha = myAsin(G, J) * 180# / PI
        mRecoGamma = 0#
        
        mRecoShiftX = Me.GetData(0, 3)
        mRecoShiftY = Me.GetData(1, 3)
        mRecoShiftZ = Me.GetData(2, 3)

        Write #1, "reco alpha = " + Trim(Str(mRecoAlpha))
        Write #1, "reco beta  = " + Trim(Str(mRecoBeta))
        Write #1, "reco gamma = " + Trim(Str(mRecoGamma))
        
        Write #2, "reco alpha = " + Trim(Str(mRecoAlpha))
        Write #2, "reco beta  = " + Trim(Str(mRecoBeta))
        Write #2, "reco gamma = " + Trim(Str(mRecoGamma))
        
        Exit Sub
    End If
    
    If (Round(Me.GetData(0, 2), TOLERANCE) = -1#) Then
        ' sin(beta) = -1
        ' this is the case when beta = -90

        ' H = sin(alpha-gamma)
        H = Me.GetData(1, 0)
        ' K = cos(alpha-gamma)
        K = Me.GetData(1, 1)

        mRecoBeta = -90#
        mRecoAlpha = myAsin(H, K) * 180# / PI
        mRecoGamma = 0#
        
        mRecoShiftX = Me.GetData(0, 3)
        mRecoShiftY = Me.GetData(1, 3)
        mRecoShiftZ = Me.GetData(2, 3)

        Write #1, "reco alpha = " + Trim(Str(mRecoAlpha))
        Write #1, "reco beta  = " + Trim(Str(mRecoBeta))
        Write #1, "reco gamma = " + Trim(Str(mRecoGamma))
        
        Write #2, "reco alpha = " + Trim(Str(mRecoAlpha))
        Write #2, "reco beta  = " + Trim(Str(mRecoBeta))
        Write #2, "reco gamma = " + Trim(Str(mRecoGamma))

        Exit Sub
    End If
    
    ' TODO find a nicer way
    
'    If (Round(Me.GetData(0, 0), TOLERANCE) = 0# And _
'        Round(Me.GetData(1, 0), TOLERANCE) = 1# And _
'        Round(Me.GetData(2, 0), TOLERANCE) = 0# And _
'        Round(Me.GetData(1, 1), TOLERANCE) = 0# And _
'        Round(Me.GetData(1, 2), TOLERANCE) = 0#) Then
'
'        mRecoBeta = myAsin(Me.GetData(0, 2), Me.GetData(2, 2)) * 180# / PI
'        mRecoAlpha = 90#
'        mRecoGamma = 0#
'
'        mRecoShiftX = Me.GetData(0, 3)
'        mRecoShiftY = Me.GetData(1, 3)
'        mRecoShiftZ = Me.GetData(2, 3)
'
'        Write #1, "reco alpha = " + Trim(Str(mRecoAlpha))
'        Write #1, "reco beta  = " + Trim(Str(mRecoBeta))
'        Write #1, "reco gamma = " + Trim(Str(mRecoGamma))
'
'        Write #2, "reco alpha = " + Trim(Str(mRecoAlpha))
'        Write #2, "reco beta  = " + Trim(Str(mRecoBeta))
'        Write #2, "reco gamma = " + Trim(Str(mRecoGamma))
'
'        Exit Sub
'    End If


    If (Round(Me.GetData(0, 0), TOLERANCE) = 0#) Then
    
        mRecoBeta = myAsin(Me.GetData(0, 2), -Me.GetData(0, 1)) * 180# / PI
        mRecoAlpha = 90#
        mRecoGamma = myAsin(Me.GetData(2, 0), Me.GetData(1, 0)) * 180# / PI

        mRecoShiftX = Me.GetData(0, 3)
        mRecoShiftY = Me.GetData(1, 3)
        mRecoShiftZ = Me.GetData(2, 3)

        Write #1, "reco alpha = " + Trim(Str(mRecoAlpha))
        Write #1, "reco beta  = " + Trim(Str(mRecoBeta))
        Write #1, "reco gamma = " + Trim(Str(mRecoGamma))

        Write #2, "reco alpha = " + Trim(Str(mRecoAlpha))
        Write #2, "reco beta  = " + Trim(Str(mRecoBeta))
        Write #2, "reco gamma = " + Trim(Str(mRecoGamma))

        Exit Sub
    End If
    
    ' A = sin(beta) / (cos(beta)*cos(beta))
    A = Me.GetData(0, 2) / (1# - Me.GetData(0, 2) * Me.GetData(0, 2))
    
    ' B = sin(alpha) * cos(gamma)
    B = Me.GetData(1, 0) + A * Me.GetData(1, 2) * Me.GetData(0, 0)
    
    ' C = cos(alpha) * sin(gamma)
    C = Me.GetData(2, 1) + A * Me.GetData(2, 2) * Me.GetData(0, 1)
    
    ' D = cos(alpha) * cos(gamma)
    D = Me.GetData(1, 1) + A * Me.GetData(1, 2) * Me.GetData(0, 1)
    
    ' F = sin(alpha) * sin(gamma)
    F = Me.GetData(2, 0) + A * Me.GetData(2, 2) * Me.GetData(0, 0)
    
    ' G = sin(alpha+gamma)
    G = B + C
    ' J = cos(alpha+gamma)
    J = D - F
    
    ' H = sin(alpha-gamma)
    H = B - C
    ' K = cos(alpha-gamma)
    K = D + F
    
    ' L = sin(gamma-alpha)
    L = C - B
    ' M = cos(gamma-alpha)
    M = D + F

    Write #1, "A = " + Trim(Str(A))
    Write #1, "B = " + Trim(Str(B))
    Write #1, "C = " + Trim(Str(C))
    Write #1, "D = " + Trim(Str(D))
    Write #1, "F = " + Trim(Str(F))

    Write #1, "G = " + Trim(Str(G))
    Write #1, "J = " + Trim(Str(J))
    Write #1, "H = " + Trim(Str(H))
    Write #1, "K = " + Trim(Str(K))
    Write #1, "L = " + Trim(Str(L))
    Write #1, "M = " + Trim(Str(M))

    Dim a_plus_g_1 As Double
    Dim a_plus_g_2 As Double
    Dim a_minus_g_1 As Double
    Dim a_minus_g_2 As Double
    Dim g_minus_a_1 As Double
    Dim recAlpha1 As Double
    Dim recGamma1 As Double
    Dim recAlpha2 As Double
    Dim recGamma2 As Double
    Dim tga1 As Double
    Dim tga2 As Double
    Dim tgg1 As Double
    Dim tgg2 As Double

    ' alpha+gamma ver1
    a_plus_g_1 = myAsin(G, J) * 180# / PI
    ' alpha+gamma ver2
    'a_plus_g_2 = myAcos(J) * 180# / PI
    
    ' alpha-gamma ver1
    a_minus_g_1 = myAsin(H, K) * 180# / PI
    ' alpha-gamma ver2
    'a_minus_g_2 = myAcos(K) * 180# / PI
    
    ' gamma-alpha ver1 (and only?)
    g_minus_a_1 = myAsin(L, M) * 180# / PI
    
    recAlpha1 = (a_plus_g_1 + a_minus_g_1) / 2#
    recGamma1 = (a_plus_g_1 - a_minus_g_1) / 2#
    
    recAlpha2 = (a_plus_g_1 + g_minus_a_1) / 2#
    recGamma2 = (a_plus_g_1 - g_minus_a_1) / 2#
    
    ' tg(alpha) ver1
    'tga1 = B / D
    ' tg(alpha) ver2
    'tga2 = F / C
    
    ' tg(gamma) ver1
    'tgg1 = F / B
    ' tg(gamma) ver2
    'tgg2 = C / D

    ' Me.GetData(0, 0)  equals  cos(alpha) * cos(beta)
    Dim cosAlpha1 As Double
    Dim cosAlpha2 As Double
    Dim cosBeta1 As Double
    Dim cosBeta2 As Double
    Dim recBeta1 As Double
    Dim recBeta2 As Double
    
    cosAlpha1 = Cos(recAlpha1 * PI / 180#)
    cosAlpha2 = Cos(recAlpha2 * PI / 180#)
    cosBeta1 = Me.GetData(0, 0) / cosAlpha1
    cosBeta2 = Me.GetData(0, 0) / cosAlpha2
    recBeta1 = myAsin(Me.GetData(0, 2), cosBeta1) * 180# / PI
    recBeta2 = myAsin(Me.GetData(0, 2), cosBeta2) * 180# / PI

    Write #1, "sin(beta)          = " + Trim(Str(Me.GetData(0, 2)))
    Write #1, "cos(beta)   (ver1) = " + Trim(Str(cosBeta1))
    Write #1, "cos(beta)   (ver2) = " + Trim(Str(cosBeta2))

    Write #1, "alpha+gamma (ver1) = " + Trim(Str(a_plus_g_1))
    'Write #1, "alpha+gamma (ver2) = " + Trim(Str(a_plus_g_2))

    Write #1, "alpha-gamma (ver1) = " + Trim(Str(a_minus_g_1))
    'Write #1, "alpha-gamma (ver2) = " + Trim(Str(a_minus_g_2))

    Write #1, "gamma-alpha (ver1) = " + Trim(Str(g_minus_a_1))

    'Write #1, "tg(alpha)  (ver1)  = " + Trim(Str(tga1))
    'Write #1, "tg(alpha)  (ver2)  = " + Trim(Str(tga2))
    'Write #1, "tg(gamma)  (ver1)  = " + Trim(Str(tgg1))
    'Write #1, "tg(gamma)  (ver2)  = " + Trim(Str(tgg2))

    Write #1, "reco alpha  (ver1) = " + Trim(Str(recAlpha1))
    Write #1, "reco alpha  (ver2) = " + Trim(Str(recAlpha2))
    Write #1, "reco gamma  (ver1) = " + Trim(Str(recGamma1))
    Write #1, "reco gamma  (ver2) = " + Trim(Str(recGamma2))
    Write #1, "reco beta   (ver1) = " + Trim(Str(recBeta1))
    Write #1, "reco beta   (ver2) = " + Trim(Str(recBeta2))

    Write #2, "reco alpha  (ver1) = " + Trim(Str(recAlpha1))
    Write #2, "reco alpha  (ver2) = " + Trim(Str(recAlpha2))
    Write #2, "reco gamma  (ver1) = " + Trim(Str(recGamma1))
    Write #2, "reco gamma  (ver2) = " + Trim(Str(recGamma2))
    Write #2, "reco beta   (ver1) = " + Trim(Str(recBeta1))
    Write #2, "reco beta   (ver2) = " + Trim(Str(recBeta2))

    mRecoAlpha = recAlpha1
    mRecoBeta = recBeta1
    mRecoGamma = recGamma1
    
    mRecoShiftX = Me.GetData(0, 3)
    mRecoShiftY = Me.GetData(1, 3)
    mRecoShiftZ = Me.GetData(2, 3)
    
End Sub

Public Function myArcsin(x As Double) As Double
'    If (Round(x, TOLERANCE) = 1) Then
'        myArcsin = PI / 2#
'    ElseIf Round(x, TOLERANCE) = -1 Then
'        myArcsin = -PI / 2#
'    Else
        myArcsin = Atn(x / Sqr(-x * x + 1#))
'    End If
End Function

' return radians - same way as asin() of <cmath>
Public Function myAsin(sinAlpha As Double, cosAlpha As Double) As Double

    Dim sinAlpha2 As Double
    Dim cosAlpha2 As Double
    
    sinAlpha2 = Round(sinAlpha, TOLERANCE)
    cosAlpha2 = Round(cosAlpha, TOLERANCE)

    If (sinAlpha2 = 0# And cosAlpha2 = 1#) Then
        myAsin = 0#
        Exit Function
    End If
    
    If (sinAlpha2 = 1# And cosAlpha2 = 0#) Then
        myAsin = PI / 2#
        Exit Function
    End If
    
    If (sinAlpha2 = 0# And cosAlpha2 = -1#) Then
        myAsin = PI
        Exit Function
    End If
    
    If (sinAlpha2 = -1# And cosAlpha2 = 0#) Then
        myAsin = -PI / 2#
        Exit Function
    End If

    If (sinAlpha2 > 0#) Then
        If (cosAlpha2 > 0#) Then
            myAsin = myArcsin(sinAlpha2)
        Else
            myAsin = PI - myArcsin(sinAlpha2)
        End If
    Else
        If (cosAlpha2 > 0#) Then
            myAsin = 2# * PI + myArcsin(sinAlpha2)
        Else
            myAsin = PI - myArcsin(sinAlpha2)
        End If
    End If
    
End Function

Attribute VB_Name = "Matrix3by3"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' Matrix3by3 class

' First index is column index, second - row index

' | 0,0 | 1,0 | 2,0 |
' | 0,1 | 1,1 | 2,1 |
' | 0,2 | 1,2 | 2,2 |

Option Explicit

Const PI = 3.14159265358979

Private mData(8) As Double

' Constructor
Public Sub Class_Initialize()
    Call InitE
End Sub

' Init with unity diagonal matrix E
Public Sub InitE()
    Dim iCol As Integer
    Dim jRow As Integer
    For jRow = 0 To 2
        For iCol = 0 To 2
            If iCol = jRow Then
                Me.SetData iCol, jRow, 1#
            Else
                Me.SetData iCol, jRow, 0#
            End If
        Next iCol
    Next jRow
End Sub

' Accessor
Public Function GetData(iCol As Integer, jRow As Integer) As Double
    GetData = mData(iCol * 3 + jRow)
End Function

' Modifier
Public Sub SetData(iCol As Integer, jRow As Integer, newVal As Double)
    mData(iCol * 3 + jRow) = newVal
End Sub

Public Sub Dump(preMessage As String)
    ' Tolerance in this round function calls does not matter -
    ' it is just for nice number printing
    Dim tol As Integer
    tol = 12
    Dim message As String
    message = preMessage + vbNewLine + _
           "| " + Str(Round(Me.GetData(0, 0), tol)) + vbTab + _
           "| " + Str(Round(Me.GetData(1, 0), tol)) + vbTab + _
           "| " + Str(Round(Me.GetData(2, 0), tol)) + vbNewLine + _
           "| " + Str(Round(Me.GetData(0, 1), tol)) + vbTab + _
           "| " + Str(Round(Me.GetData(1, 1), tol)) + vbTab + _
           "| " + Str(Round(Me.GetData(2, 1), tol)) + vbNewLine + _
           "| " + Str(Round(Me.GetData(0, 2), tol)) + vbTab + _
           "| " + Str(Round(Me.GetData(1, 2), tol)) + vbTab + _
           "| " + Str(Round(Me.GetData(2, 2), tol))
    Write #1, message
    Write #1, vbNewLine
    'MsgBox message
End Sub

' Construct as minor of a bigger matrix
Public Sub Construct(mat4by4 As Matrix, iCol As Integer, jRow As Integer)

    Dim i3by3 As Integer ' index in the current 3 by 3 matrix
    Dim j3by3 As Integer ' index in the current 3 by 3 matrix
    Dim i4by4 As Integer ' index in the source 4 by 4 matrix
    Dim j4by4 As Integer ' index in the source 4 by 4 matrix
    
    For i3by3 = 0 To 2
        For j3by3 = 0 To 2
            i4by4 = i3by3
            j4by4 = j3by3
            If (i3by3 >= iCol) Then
                i4by4 = i4by4 + 1
            End If
            If (j3by3 >= jRow) Then
                j4by4 = j4by4 + 1
            End If
            Me.SetData i3by3, j3by3, mat4by4.GetData(i4by4, j4by4)
        Next j3by3
    Next i3by3
    
End Sub

Public Function Det() As Double
    Det = Me.GetData(0, 0) * Me.GetData(1, 1) * Me.GetData(2, 2) + _
          Me.GetData(1, 0) * Me.GetData(2, 1) * Me.GetData(0, 2) + _
          Me.GetData(0, 1) * Me.GetData(1, 2) * Me.GetData(2, 0) - _
          Me.GetData(2, 0) * Me.GetData(1, 1) * Me.GetData(0, 2) - _
          Me.GetData(0, 0) * Me.GetData(2, 1) * Me.GetData(1, 2) - _
          Me.GetData(0, 1) * Me.GetData(1, 0) * Me.GetData(2, 2)
End Function

Attribute VB_Name = "UserForm1"
Attribute VB_Base = "0{5C4442C1-0DAD-4534-96C3-802758DEEE08}{F4D31932-3ED0-4D3D-9111-97C06CAE0444}"
Attribute VB_GlobalNameSpace = False
Attribute VB_Creatable = False
Attribute VB_PredeclaredId = True
Attribute VB_Exposed = False
Attribute VB_TemplateDerived = False
Attribute VB_Customizable = False
Option Explicit

Const TOLERANCE = 12

' Frequently used parameters (SetAnglesCS3fixed)
Dim paramAlpha As Parameter
Dim paramBeta As Parameter
Dim paramGamma As Parameter
' Frequently used parameters (ApplyAnglesToCS3)
Dim parArray(5) As Parameter
' Frequently used points (QA)
Dim recoXpoint 'As HybridShapePointCoord
Dim recoYpoint 'As HybridShapePointCoord
Dim recoZpoint 'As HybridShapePointCoord
Dim recoOrigin 'As HybridShapePointCoord
Dim origXpoint 'As HybridShapePointCoord
Dim origYpoint 'As HybridShapePointCoord
Dim origZpoint 'As HybridShapePointCoord
Dim origOrigin 'As HybridShapePointCoord
    
Private Sub CommandButton1_Click()
    
    ' Open text file for debug info
    Open UserForm1.TextBox1.Text For Output As #1
    Open UserForm1.TextBox2.Text For Output As #2
    
    Write #1, Time
    Write #2, Time
    
    Dim prtDoc As PartDocument
    Dim prt As Part
    Dim hbds As HybridBodies
    Dim fact As HybridShapeFactory
    
    Dim geomSet3 As HybridBody
    Dim geomSet3fixed As HybridBody
    Dim geomSetHshps3 As HybridShapes
    Dim geomSetHshps3fixed As HybridShapes
    
    Set prtDoc = CATIA.ActiveDocument
    Set prt = prtDoc.Part
    Set hbds = prt.HybridBodies
    Set fact = prt.HybridShapeFactory
    
    Set geomSet3 = hbds.GetItem("Geometrical Set.CS3")
    Set geomSet3fixed = hbds.GetItem("Geometrical Set.CS3fixed")
    Set geomSetHshps3 = geomSet3.HybridShapes
    Set geomSetHshps3fixed = geomSet3fixed.HybridShapes

    ' --------------------------------------------------------------
    ' Store the pointers to some frequently used parameters
    ' --------------------------------------------------------------

    Dim params As Parameters
    Set params = prt.Parameters
    
    ' (SetAnglesCS3fixed)
    Set paramAlpha = params.GetItem("Geometrical Set.CS3fixed\Rotate.Z\Angle")
    Set paramBeta = params.GetItem("Geometrical Set.CS3fixed\Rotate.Y\Angle")
    Set paramGamma = params.GetItem("Geometrical Set.CS3fixed\Rotate.X\Angle")
    
    ' (ApplyAnglesToCS3)
    Set parArray(0) = params.GetItem("Geometrical Set.CS3\Rotate.Z\Angle")
    Set parArray(1) = params.GetItem("Geometrical Set.CS3\Rotate.Y\Angle")
    Set parArray(2) = params.GetItem("Geometrical Set.CS3\Rotate.X\Angle")
    Set parArray(3) = params.GetItem("Geometrical Set.CS3\Translate.2\X")
    Set parArray(4) = params.GetItem("Geometrical Set.CS3\Translate.2\Y")
    Set parArray(5) = params.GetItem("Geometrical Set.CS3\Translate.2\Z")

    ' --------------------------------------------------------------
    ' Store the pointers to some frequently used points (QA)
    ' --------------------------------------------------------------

    Set recoXpoint = geomSetHshps3.GetItem("Point.S")
    Set recoYpoint = geomSetHshps3.GetItem("Point.T")
    Set recoZpoint = geomSetHshps3.GetItem("Point.U")
    Set recoOrigin = geomSetHshps3.GetItem("Point.V")
    Set origXpoint = geomSetHshps3fixed.GetItem("Point.Sfixed")
    Set origYpoint = geomSetHshps3fixed.GetItem("Point.Tfixed")
    Set origZpoint = geomSetHshps3fixed.GetItem("Point.Ufixed")
    Set origOrigin = geomSetHshps3fixed.GetItem("Point.Vfixed")

    ' --------------------------------------------------------------
    ' Define some known angles and translations
    ' --------------------------------------------------------------
    
    Dim alpha1 As Double
    Dim beta1 As Double
    Dim gamma1 As Double
    Dim shiftX1 As Double
    Dim shiftY1 As Double
    Dim shiftZ1 As Double
    
    alpha1 = 10# ' rotation Z
    beta1 = 20#  ' rotation Y
    gamma1 = 30# ' rotation X
    shiftX1 = 3.3
    shiftY1 = 4.4
    shiftZ1 = 5.5
    
    ' --------------------------------------------------------------
    ' Build matrices from known angles and translations
    ' --------------------------------------------------------------

    Dim Mtxyz1 As New Matrix
    Mtxyz1.InitTXYZ alpha1, beta1, gamma1, shiftX1, shiftY1, shiftZ1

    ' --------------------------------------------------------------
    '
    ' --------------------------------------------------------------

    Dim startAlpha2 As Double
    Dim startBeta2 As Double
    Dim startGamma2 As Double
    Dim endAlpha2 As Double
    Dim endBeta2 As Double
    Dim endGamma2 As Double
    Dim stepAlpha2 As Double
    Dim stepBeta2 As Double
    Dim stepGamma2 As Double

    startAlpha2 = 0#
    startBeta2 = 0#
    startGamma2 = 0#
    endAlpha2 = 360#
    endBeta2 = 360#
    endGamma2 = 360#
    stepAlpha2 = 30#
    stepBeta2 = 30#
    stepGamma2 = 30#

    Dim iAlpha2 As Integer
    Dim iBeta2 As Integer
    Dim iGamma2 As Integer

    For iAlpha2 = 0 To ((endAlpha2 - startAlpha2) / stepAlpha2)
    For iBeta2 = 0 To ((endBeta2 - startBeta2) / stepBeta2)
    For iGamma2 = 0 To ((endGamma2 - startGamma2) / stepGamma2)
    
        Dim currentAlpha2 As Double
        Dim currentBeta2 As Double
        Dim currentGamma2 As Double

        currentAlpha2 = startAlpha2 + iAlpha2 * stepAlpha2
        currentBeta2 = startBeta2 + iBeta2 * stepBeta2
        currentGamma2 = startGamma2 + iGamma2 * stepGamma2

        Call SetAnglesCS3fixed(currentAlpha2, currentBeta2, currentGamma2)

        Write #1, "Original alpha2/beta2/gamma2: " + Trim(Str(currentAlpha2)) + vbTab + _
                   Trim(Str(currentBeta2)) + vbTab + Trim(Str(currentGamma2))
        Write #2, "Original alpha2/beta2/gamma2: " + Trim(Str(currentAlpha2)) + vbTab + _
                   Trim(Str(currentBeta2)) + vbTab + Trim(Str(currentGamma2))

        ' -----------------------------------------------------

        Dim M3fixed As New Matrix
        M3fixed.InitBy4Points geomSetHshps3fixed.GetItem("Point.Sfixed"), _
                              geomSetHshps3fixed.GetItem("Point.Tfixed"), _
                              geomSetHshps3fixed.GetItem("Point.Ufixed"), _
                              geomSetHshps3fixed.GetItem("Point.Vfixed")
        'M3fixed.Dump "Extracted M3fixed"

        ' --------------------------------------------------------------
    
        Dim Mtxyz1inv As New Matrix
        Set Mtxyz1inv = Mtxyz1.Inverse
        'Mtxyz1inv.Dump "Mtxyz1 Inv."
        
        M3fixed.Multiply Mtxyz1inv
        M3fixed.Dump "M3fixed * Mtxyz1 Inv."
        M3fixed.ExtractAnglesAndCoordinates
    
        ' Apply reconstructed angles to the CS3 (not fixed)
        Call ApplyAnglesToCS3(M3fixed)
        
        ' Measure the distance between corresponding points
        Call QA
    
        ' --------------------------------------------------------------

    Next iGamma2
    Next iBeta2
    Next iAlpha2
    
    Write #1, Time
    Write #2, Time
    
    ' Close output debug text file
    Close #1
    Close #2

    MsgBox "Done!"

End Sub

Private Sub SetAnglesCS3fixed(alpha As Double, beta As Double, gamma As Double)
    paramAlpha.ValuateFromString (Trim(Str(alpha)) + "deg")
    paramBeta.ValuateFromString (Trim(Str(beta)) + "deg")
    paramGamma.ValuateFromString (Trim(Str(gamma)) + "deg")
    CATIA.ActiveDocument.Part.Update
End Sub

Private Sub ApplyAnglesToCS3(M As Matrix)
    parArray(0).ValuateFromString Trim(Str(M.mRecoAlpha)) + "deg"
    parArray(1).ValuateFromString Trim(Str(M.mRecoBeta)) + "deg"
    parArray(2).ValuateFromString Trim(Str(M.mRecoGamma)) + "deg"
    parArray(3).ValuateFromString Trim(Str(M.mRecoShiftX)) + "mm"
    parArray(4).ValuateFromString Trim(Str(M.mRecoShiftY)) + "mm"
    parArray(5).ValuateFromString Trim(Str(M.mRecoShiftZ)) + "mm"
    CATIA.ActiveDocument.Part.Update
End Sub

Private Sub QA()

    Dim coordsVarXdir(2) As Variant
    Dim coordsVarYdir(2) As Variant
    Dim coordsVarZdir(2) As Variant
    Dim coordsVarOrigin(2) As Variant
    
    Dim coordsRecoDouble(11) As Double

    recoXpoint.GetCoordinates coordsVarXdir
    recoYpoint.GetCoordinates coordsVarYdir
    recoZpoint.GetCoordinates coordsVarZdir
    recoOrigin.GetCoordinates coordsVarOrigin

    coordsRecoDouble(0) = coordsVarXdir(0) ' Xdir point - coordinate x
    coordsRecoDouble(1) = coordsVarXdir(1) ' Xdir point - coordinate y
    coordsRecoDouble(2) = coordsVarXdir(2) ' Xdir point - coordinate z
    coordsRecoDouble(3) = coordsVarYdir(0) ' Ydir point - coordinate x
    coordsRecoDouble(4) = coordsVarYdir(1) ' Ydir point - coordinate y
    coordsRecoDouble(5) = coordsVarYdir(2) ' Ydir point - coordinate z
    coordsRecoDouble(6) = coordsVarZdir(0) ' Zdir point - coordinate x
    coordsRecoDouble(7) = coordsVarZdir(1) ' Zdir point - coordinate y
    coordsRecoDouble(8) = coordsVarZdir(2) ' Zdir point - coordinate z
    coordsRecoDouble(9) = coordsVarOrigin(0) ' origin - coordinate x
    coordsRecoDouble(10) = coordsVarOrigin(1) ' origin - coordinate y
    coordsRecoDouble(11) = coordsVarOrigin(2) ' origin - coordinate z
    
    Dim coordsOrigDouble(11) As Double

    origXpoint.GetCoordinates coordsVarXdir
    origYpoint.GetCoordinates coordsVarYdir
    origZpoint.GetCoordinates coordsVarZdir
    origOrigin.GetCoordinates coordsVarOrigin

    coordsOrigDouble(0) = coordsVarXdir(0) ' Xdir point - coordinate x
    coordsOrigDouble(1) = coordsVarXdir(1) ' Xdir point - coordinate y
    coordsOrigDouble(2) = coordsVarXdir(2) ' Xdir point - coordinate z
    coordsOrigDouble(3) = coordsVarYdir(0) ' Ydir point - coordinate x
    coordsOrigDouble(4) = coordsVarYdir(1) ' Ydir point - coordinate y
    coordsOrigDouble(5) = coordsVarYdir(2) ' Ydir point - coordinate z
    coordsOrigDouble(6) = coordsVarZdir(0) ' Zdir point - coordinate x
    coordsOrigDouble(7) = coordsVarZdir(1) ' Zdir point - coordinate y
    coordsOrigDouble(8) = coordsVarZdir(2) ' Zdir point - coordinate z
    coordsOrigDouble(9) = coordsVarOrigin(0) ' origin - coordinate x
    coordsOrigDouble(10) = coordsVarOrigin(1) ' origin - coordinate y
    coordsOrigDouble(11) = coordsVarOrigin(2) ' origin - coordinate z
        
    Dim tol As Integer
    tol = 12
    
    Dim diff(11) As Double
    
    Dim i As Integer
    For i = 0 To 11
        diff(i) = coordsRecoDouble(i) - coordsOrigDouble(i)
        Write #2, Trim(Str(coordsOrigDouble(i))) + vbTab + _
                  Trim(Str(coordsRecoDouble(i))) + vbTab + _
                  Trim(Str(Round(diff(i), tol)))
    Next i

'    Write #2, "Xort X" + vbTab + Trim(Str(coordsOrigDouble(0))) + vbTab + _
'                                 Trim(Str(coordsRecoDouble(0))) + vbTab + _
'                                 Trim(Str(Round(coordsRecoDouble(0) - coordsOrigDouble(0), tol)))
'    Write #2, "Xort Y" + vbTab + Trim(Str(coordsOrigDouble(1))) + vbTab + _
'                                 Trim(Str(coordsRecoDouble(1))) + vbTab + _
'                                 Trim(Str(Round(coordsRecoDouble(1) - coordsOrigDouble(1), tol)))
'    Write #2, "Xort Z" + vbTab + Trim(Str(coordsOrigDouble(2))) + vbTab + _
'                                 Trim(Str(coordsRecoDouble(2))) + vbTab + _
'                                 Trim(Str(Round(coordsRecoDouble(2) - coordsOrigDouble(2), tol)))
'    Write #2, "Yort X" + vbTab + Trim(Str(coordsOrigDouble(3))) + vbTab + _
'                                 Trim(Str(coordsRecoDouble(3))) + vbTab + _
'                                 Trim(Str(Round(coordsRecoDouble(3) - coordsOrigDouble(3), tol)))
'    Write #2, "Yort Y" + vbTab + Trim(Str(coordsOrigDouble(4))) + vbTab + _
'                                 Trim(Str(coordsRecoDouble(4))) + vbTab + _
'                                 Trim(Str(Round(coordsRecoDouble(4) - coordsOrigDouble(4), tol)))
'    Write #2, "Yort Z" + vbTab + Trim(Str(coordsOrigDouble(5))) + vbTab + _
'                                 Trim(Str(coordsRecoDouble(5))) + vbTab + _
'                                 Trim(Str(Round(coordsRecoDouble(5) - coordsOrigDouble(5), tol)))
'    Write #2, "Zort X" + vbTab + Trim(Str(coordsOrigDouble(6))) + vbTab + _
'                                 Trim(Str(coordsRecoDouble(6))) + vbTab + _
'                                 Trim(Str(Round(coordsRecoDouble(6) - coordsOrigDouble(6), tol)))
'    Write #2, "Zort Y" + vbTab + Trim(Str(coordsOrigDouble(7))) + vbTab + _
'                                 Trim(Str(coordsRecoDouble(7))) + vbTab + _
'                                 Trim(Str(Round(coordsRecoDouble(7) - coordsOrigDouble(7), tol)))
'    Write #2, "Zort Z" + vbTab + Trim(Str(coordsOrigDouble(8))) + vbTab + _
'                                 Trim(Str(coordsRecoDouble(8))) + vbTab + _
'                                 Trim(Str(Round(coordsRecoDouble(8) - coordsOrigDouble(8), tol)))
'    Write #2, "Orig X" + vbTab + Trim(Str(coordsOrigDouble(9))) + vbTab + _
'                                 Trim(Str(coordsRecoDouble(9))) + vbTab + _
'                                 Trim(Str(Round(coordsRecoDouble(9) - coordsOrigDouble(9), tol)))
'    Write #2, "Orig Y" + vbTab + Trim(Str(coordsOrigDouble(10))) + vbTab + _
'                                 Trim(Str(coordsRecoDouble(10))) + vbTab + _
'                                 Trim(Str(Round(coordsRecoDouble(10) - coordsOrigDouble(10), tol)))
'    Write #2, "Orig Z" + vbTab + Trim(Str(coordsOrigDouble(11))) + vbTab + _
'                                 Trim(Str(coordsRecoDouble(11))) + vbTab + _
'                                 Trim(Str(Round(coordsRecoDouble(11) - coordsOrigDouble(11), tol)))

End Sub

Private Sub CommandButton2_Click()
    End
End Sub

Private Sub UserForm_Initialize()
    UserForm1.TextBox1.Text = "E:\matrixTests\matrix3.txt"
    UserForm1.TextBox2.Text = "E:\matrixTests\matrix4.txt"
End Sub

Attribute VB_Name = "matrixTests1"
Option Explicit

Sub CATMain()
    UserForm1.Show vbModeless
End Sub
