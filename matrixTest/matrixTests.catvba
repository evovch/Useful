Attribute VB_Name = "Matrix"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' Matrix class

' First index is column index, second - row index

' | 0,0 | 1,0 | 2,0 | 3,0 |
' | 0,1 | 1,1 | 2,1 | 3,1 |
' | 0,2 | 1,2 | 2,2 | 3,2 |
' | 0,3 | 1,3 | 2,3 | 3,3 |

Option Explicit

Const PI = 3.14159265358979

Const TOLERANCE = 6

Private mData(15) As Double

' Constructor
Public Sub Class_Initialize()
    Call InitE
End Sub

' Correct but not used
'Public Function Clone() As Matrix
'    Dim theClone As New Matrix
'    Dim iCol As Integer
'    Dim jRow As Integer
'    For jRow = 0 To 3
'        For iCol = 0 To 3
'            theClone.SetData iCol, jRow, Me.GetData(iCol, jRow)
'        Next iCol
'    Next jRow
'    Set Clone = theClone
'End Function

' Copy data from the 'source' into this matrix
Public Sub Copy(source As Matrix)
    Dim iCol As Integer
    Dim jRow As Integer
    For jRow = 0 To 3
        For iCol = 0 To 3
            Me.SetData iCol, jRow, source.GetData(iCol, jRow)
        Next iCol
    Next jRow
End Sub

' Init with unity diagonal matrix E
Public Sub InitE()
    Dim iCol As Integer
    Dim jRow As Integer
    For jRow = 0 To 3
        For iCol = 0 To 3
            If iCol = jRow Then
                Me.SetData iCol, jRow, 1#
            Else
                Me.SetData iCol, jRow, 0#
            End If
        Next iCol
    Next jRow
End Sub

' Accessor
Public Function GetData(iCol As Integer, jRow As Integer) As Double
    GetData = mData(iCol * 4 + jRow)
End Function

' Modifier
Public Sub SetData(iCol As Integer, jRow As Integer, newVal As Double)
    mData(iCol * 4 + jRow) = newVal
End Sub

Public Sub Init4x4(p_a11 As Double, p_a12 As Double, p_a13 As Double, p_a14 As Double, _
                   p_a21 As Double, p_a22 As Double, p_a23 As Double, p_a24 As Double, _
                   p_a31 As Double, p_a32 As Double, p_a33 As Double, p_a34 As Double, _
                   p_a41 As Double, p_a42 As Double, p_a43 As Double, p_a44 As Double)
                   
    mData(0, 0) = p_a11
    mData(0, 1) = p_a21
    mData(0, 2) = p_a31
    mData(0, 3) = p_a41
    
    mData(1, 0) = p_a12
    mData(1, 1) = p_a22
    mData(1, 2) = p_a32
    mData(1, 3) = p_a42
    
    mData(2, 0) = p_a13
    mData(2, 1) = p_a23
    mData(2, 2) = p_a33
    mData(2, 3) = p_a43
    
    mData(3, 0) = p_a14
    mData(3, 1) = p_a24
    mData(3, 2) = p_a34
    mData(3, 3) = p_a44
    
End Sub

Public Sub Dump(preMessage As String)
    ' Tolerance in this round function calls does not matter -
    ' it is just for nice number printing
    Dim message As String
    message = preMessage + vbNewLine + _
           "| " + Str(Round(Me.GetData(0, 0), 6)) + vbTab + _
           "| " + Str(Round(Me.GetData(1, 0), 6)) + vbTab + _
           "| " + Str(Round(Me.GetData(2, 0), 6)) + vbTab + _
           "| " + Str(Round(Me.GetData(3, 0), 6)) + vbNewLine + _
           "| " + Str(Round(Me.GetData(0, 1), 6)) + vbTab + _
           "| " + Str(Round(Me.GetData(1, 1), 6)) + vbTab + _
           "| " + Str(Round(Me.GetData(2, 1), 6)) + vbTab + _
           "| " + Str(Round(Me.GetData(3, 1), 6)) + vbNewLine + _
           "| " + Str(Round(Me.GetData(0, 2), 6)) + vbTab + _
           "| " + Str(Round(Me.GetData(1, 2), 6)) + vbTab + _
           "| " + Str(Round(Me.GetData(2, 2), 6)) + vbTab + _
           "| " + Str(Round(Me.GetData(3, 2), 6)) + vbNewLine + _
           "| " + Str(Round(Me.GetData(0, 3), 6)) + vbTab + _
           "| " + Str(Round(Me.GetData(1, 3), 6)) + vbTab + _
           "| " + Str(Round(Me.GetData(2, 3), 6)) + vbTab + _
           "| " + Str(Round(Me.GetData(3, 3), 6))
    Write #1, message
    Write #1, vbNewLine
    'MsgBox message
End Sub

Public Sub InitTXYZ(rotZ As Double, _
                    rotY As Double, _
                    rotX As Double, _
                    trX As Double, _
                    trY As Double, _
                    trZ As Double)

    Dim Mz As New Matrix ' rotation around Z
    Dim My As New Matrix ' rotation around Y
    Dim Mx As New Matrix ' rotation around X
    Dim Mtr As New Matrix ' translation
    Dim Mtxyz As New Matrix ' all four together

    Mz.InitZrot -rotZ
    My.InitYrot -rotY
    Mx.InitXrot -rotX
    Mtr.InitXYZposRow trX, trY, trZ
    'Mz.Dump "Mz (rot. around Z) alpha=" + Trim(Str(rotZ))
    'My.Dump "My (rot. around Y) beta=" + Trim(Str(rotY))
    'Mx.Dump "Mx (rot. around X) gamma=" + Trim(Str(rotX))
    'Mtr.Dump "Mtr (tr. along X, Y, and Z) trX=" + Trim(Str(trX)) + _
                                        " trY=" + Trim(Str(trY)) + _
                                        " trZ=" + Trim(Str(trZ))

    Mtxyz.InitE
    'Mtxyz.Dump "Mtxyz (E - initial state)"
    Mtxyz.Multiply Mz
    'Mtxyz.Dump "Mtxyz (E*Mz)"
    Mtxyz.Multiply My
    'Mtxyz.Dump "Mtxyz (E*Mz*My)"
    Mtxyz.Multiply Mx
    'Mtxyz.Dump "Mtxyz (E*Mz*My*Mx)"
    Mtxyz.Multiply Mtr
    'Mtxyz.Dump "Mtxyz (E*Mz*My*Mx*Mtr)"

    Me.Copy Mtxyz

End Sub

Public Sub InitXrot(gammaDeg As Double)

    Dim gamma As Double
    gamma = gammaDeg * PI / 180#

    Me.SetData 0, 0, 1#
    Me.SetData 0, 1, 0#
    Me.SetData 0, 2, 0#
    Me.SetData 0, 3, 0#
    
    Me.SetData 1, 0, 0#
    Me.SetData 1, 1, Cos(gamma)
    Me.SetData 1, 2, Sin(gamma)
    Me.SetData 1, 3, 0#
    
    Me.SetData 2, 0, 0#
    Me.SetData 2, 1, -Sin(gamma)
    Me.SetData 2, 2, Cos(gamma)
    Me.SetData 2, 3, 0#

    Me.SetData 3, 0, 0#
    Me.SetData 3, 1, 0#
    Me.SetData 3, 2, 0#
    Me.SetData 3, 3, 1#
    
End Sub

Public Sub InitYrot(betaDeg As Double)

    Dim beta As Double
    beta = betaDeg * PI / 180#

    Me.SetData 0, 0, Cos(beta)
    Me.SetData 0, 1, 0#
    Me.SetData 0, 2, -Sin(beta)
    Me.SetData 0, 3, 0#
    
    Me.SetData 1, 0, 0#
    Me.SetData 1, 1, 1#
    Me.SetData 1, 2, 0#
    Me.SetData 1, 3, 0#
    
    Me.SetData 2, 0, Sin(beta)
    Me.SetData 2, 1, 0#
    Me.SetData 2, 2, Cos(beta)
    Me.SetData 2, 3, 0#

    Me.SetData 3, 0, 0#
    Me.SetData 3, 1, 0#
    Me.SetData 3, 2, 0#
    Me.SetData 3, 3, 1#
    
End Sub

Public Sub InitZrot(alphaDeg As Double)

    Dim alpha As Double
    alpha = alphaDeg * PI / 180#

    Me.SetData 0, 0, Cos(alpha)
    Me.SetData 0, 1, Sin(alpha)
    Me.SetData 0, 2, 0#
    Me.SetData 0, 3, 0#
    
    Me.SetData 1, 0, -Sin(alpha)
    Me.SetData 1, 1, Cos(alpha)
    Me.SetData 1, 2, 0#
    Me.SetData 1, 3, 0#
    
    Me.SetData 2, 0, 0#
    Me.SetData 2, 1, 0#
    Me.SetData 2, 2, 1#
    Me.SetData 2, 3, 0#
    
    Me.SetData 3, 0, 0#
    Me.SetData 3, 1, 0#
    Me.SetData 3, 2, 0#
    Me.SetData 3, 3, 1#
    
End Sub

Public Sub InitXYZposRow(x As Double, y As Double, z As Double)
    Me.InitE
    Me.SetData 0, 3, x
    Me.SetData 1, 3, y
    Me.SetData 2, 3, z
End Sub

' Correct but not used
'Public Sub InitXYZposCol(x As Double, y As Double, z As Double)
'    Me.InitE
'    Me.SetData 3, 0, x
'    Me.SetData 3, 1, y
'    Me.SetData 3, 2, z
'End Sub

' Multiply currect matrix by some right operand
Public Sub Multiply(right_op As Matrix)
    Dim iCol As Integer
    Dim jRow As Integer
    Dim K As Integer
    Dim sum As Double
    Dim left_op As New Matrix
    'Set left_op = Me.Clone
    left_op.Copy Me
    For iCol = 0 To 3
        For jRow = 0 To 3
            sum = 0
            For K = 0 To 3
                sum = sum + left_op.GetData(K, jRow) * right_op.GetData(iCol, K)
            Next K
            Me.SetData iCol, jRow, sum
        Next jRow
    Next iCol
End Sub

Public Sub Transpose()
    Dim iCol As Integer
    Dim jRow As Integer
    Dim tmp As Double
    For iCol = 0 To 3
        For jRow = iCol + 1 To 3
            tmp = Me.GetData(iCol, jRow)
            Me.SetData iCol, jRow, Me.GetData(jRow, iCol)
            Me.SetData jRow, iCol, tmp
        Next jRow
    Next iCol
End Sub

Public Sub InitBy4Points(pointXdir, pointYdir, pointZdir, pointOrigin)

    Dim coordsVarXdir(2) As Variant
    Dim coordsVarYdir(2) As Variant
    Dim coordsVarZdir(2) As Variant
    Dim coordsVarOrigin(2) As Variant
    
    Dim coordsDouble(11) As Double

    pointXdir.GetCoordinates coordsVarXdir
    pointYdir.GetCoordinates coordsVarYdir
    pointZdir.GetCoordinates coordsVarZdir
    pointOrigin.GetCoordinates coordsVarOrigin

    coordsDouble(0) = coordsVarXdir(0) ' Xdir point - coordinate x
    coordsDouble(1) = coordsVarXdir(1) ' Xdir point - coordinate y
    coordsDouble(2) = coordsVarXdir(2) ' Xdir point - coordinate z
    coordsDouble(3) = coordsVarYdir(0) ' Ydir point - coordinate x
    coordsDouble(4) = coordsVarYdir(1) ' Ydir point - coordinate y
    coordsDouble(5) = coordsVarYdir(2) ' Ydir point - coordinate z
    coordsDouble(6) = coordsVarZdir(0) ' Zdir point - coordinate x
    coordsDouble(7) = coordsVarZdir(1) ' Zdir point - coordinate y
    coordsDouble(8) = coordsVarZdir(2) ' Zdir point - coordinate z
    coordsDouble(9) = coordsVarOrigin(0) ' origin - coordinate x
    coordsDouble(10) = coordsVarOrigin(1) ' origin - coordinate y
    coordsDouble(11) = coordsVarOrigin(2) ' origin - coordinate z

    Me.InitE
    Me.SetData 0, 0, coordsDouble(0) - coordsDouble(9)  ' Here's the magic
    Me.SetData 1, 0, coordsDouble(1) - coordsDouble(10) ' Here's the magic
    Me.SetData 2, 0, coordsDouble(2) - coordsDouble(11) ' Here's the magic
    Me.SetData 0, 1, coordsDouble(3) - coordsDouble(9)  ' Here's the magic
    Me.SetData 1, 1, coordsDouble(4) - coordsDouble(10) ' Here's the magic
    Me.SetData 2, 1, coordsDouble(5) - coordsDouble(11) ' Here's the magic
    Me.SetData 0, 2, coordsDouble(6) - coordsDouble(9)  ' Here's the magic
    Me.SetData 1, 2, coordsDouble(7) - coordsDouble(10) ' Here's the magic
    Me.SetData 2, 2, coordsDouble(8) - coordsDouble(11) ' Here's the magic
    Me.SetData 0, 3, coordsDouble(9)
    Me.SetData 1, 3, coordsDouble(10)
    Me.SetData 2, 3, coordsDouble(11)
    
End Sub

Public Sub CreateGeometry(fact As HybridShapeFactory, geomSet As HybridBody, suffix As String)

    ' Create new points
    Dim pCS0(3) As HybridShapePointCoord
    Set pCS0(0) = fact.AddNewPointCoord(Me.GetData(0, 3) + Me.GetData(0, 0), _
                                        Me.GetData(1, 3) + Me.GetData(1, 0), _
                                        Me.GetData(2, 3) + Me.GetData(2, 0))
    Set pCS0(1) = fact.AddNewPointCoord(Me.GetData(0, 3) + Me.GetData(0, 1), _
                                        Me.GetData(1, 3) + Me.GetData(1, 1), _
                                        Me.GetData(2, 3) + Me.GetData(2, 1))
    Set pCS0(2) = fact.AddNewPointCoord(Me.GetData(0, 3) + Me.GetData(0, 2), _
                                        Me.GetData(1, 3) + Me.GetData(1, 2), _
                                        Me.GetData(2, 3) + Me.GetData(2, 2))
    Set pCS0(3) = fact.AddNewPointCoord(Me.GetData(0, 3), Me.GetData(1, 3), Me.GetData(2, 3))
    pCS0(0).Name = "Point." + suffix + ".recoX"
    pCS0(1).Name = "Point." + suffix + ".recoY"
    pCS0(2).Name = "Point." + suffix + ".recoZ"
    pCS0(3).Name = "Point." + suffix + ".recoO"
    
    geomSet.AppendHybridShape pCS0(0)
    geomSet.AppendHybridShape pCS0(1)
    geomSet.AppendHybridShape pCS0(2)
    geomSet.AppendHybridShape pCS0(3)
    
    ' Create new lines
    Dim lCS0(2) As HybridShapeLinePtPt
    Set lCS0(0) = fact.AddNewLinePtPt(pCS0(3), pCS0(0))
    Set lCS0(1) = fact.AddNewLinePtPt(pCS0(3), pCS0(1))
    Set lCS0(2) = fact.AddNewLinePtPt(pCS0(3), pCS0(2))
    lCS0(0).Name = "Line." + suffix + ".X"
    lCS0(1).Name = "Line." + suffix + ".Y"
    lCS0(2).Name = "Line." + suffix + ".Z"
    
    geomSet.AppendHybridShape lCS0(0)
    geomSet.AppendHybridShape lCS0(1)
    geomSet.AppendHybridShape lCS0(2)

End Sub

Public Sub ExtractAnglesAndCoordinates()

    Dim A As Double
    Dim B As Double
    Dim C As Double
    Dim D As Double
    Dim F As Double
    Dim G As Double
    Dim J As Double
    Dim H As Double
    Dim K As Double
    Dim L As Double
    Dim M As Double
    
    ' A = sin(beta) / (cos(beta)*cos(beta))
    A = Me.GetData(0, 2) / (1# - Me.GetData(0, 2) * Me.GetData(0, 2))
    
    ' B = sin(alpha) * cos(gamma)
    B = Me.GetData(1, 0) + A * Me.GetData(1, 2) * Me.GetData(0, 0)
    
    ' C = cos(alpha) * sin(gamma)
    C = Me.GetData(2, 1) + A * Me.GetData(2, 2) * Me.GetData(0, 1)
    
    ' D = cos(alpha) * cos(gamma)
    D = Me.GetData(1, 1) + A * Me.GetData(1, 2) * Me.GetData(0, 1)
    
    ' F = sin(alpha) * sin(gamma)
    F = Me.GetData(2, 0) + A * Me.GetData(2, 2) * Me.GetData(0, 0)
    
    ' G = sin(alpha+gamma)
    G = B + C
    ' J = cos(alpha+gamma)
    J = D - F
    
    ' H = sin(alpha-gamma)
    H = B - C
    ' K = cos(alpha-gamma)
    K = D + F
    
    ' L = sin(gamma-alpha)
    L = C - B
    ' M = cos(gamma-alpha)
    M = D + F

'    Write #1, "A=" + Trim(Str(A))
'    Write #1, "B=" + Trim(Str(B))
'    Write #1, "C=" + Trim(Str(C))
'    Write #1, "D=" + Trim(Str(D))
'    Write #1, "F=" + Trim(Str(F))
'
'    Write #1, "G=" + Trim(Str(G))
'    Write #1, "J=" + Trim(Str(J))
'    Write #1, "H=" + Trim(Str(H))
'    Write #1, "K=" + Trim(Str(K))
'    Write #1, "L=" + Trim(Str(L))
'    Write #1, "M=" + Trim(Str(M))

'    Exit Sub

    Dim a_plus_g_1 As Double
    Dim a_plus_g_2 As Double
    Dim a_minus_g_1 As Double
    Dim a_minus_g_2 As Double
    Dim g_minus_a_1 As Double
    Dim recAlpha1 As Double
    Dim recGamma1 As Double
    Dim recAlpha2 As Double
    Dim recGamma2 As Double
    Dim tga1 As Double
    Dim tga2 As Double
    Dim tgg1 As Double
    Dim tgg2 As Double

    ' alpha+gamma ver1
    a_plus_g_1 = myAsin(G, J) * 180# / PI
    ' alpha+gamma ver2
    'a_plus_g_2 = myAcos(J) * 180# / PI
    
    ' alpha-gamma ver1
    a_minus_g_1 = myAsin(H, K) * 180# / PI
    ' alpha-gamma ver2
    'a_minus_g_2 = myAcos(K) * 180# / PI
    
    ' gamma-alpha ver1 (and only?)
    g_minus_a_1 = myAsin(L, M) * 180# / PI
    
    recAlpha1 = (a_plus_g_1 + a_minus_g_1) / 2#
    recGamma1 = (a_plus_g_1 - a_minus_g_1) / 2#
    
    recAlpha2 = (a_plus_g_1 + g_minus_a_1) / 2#
    recGamma2 = (a_plus_g_1 - g_minus_a_1) / 2#
    
    ' tg(alpha) ver1
    tga1 = B / D
    ' tg(alpha) ver2
    tga2 = F / C
    
    ' tg(gamma) ver1
    tgg1 = F / B
    ' tg(gamma) ver2
    tgg2 = C / D

'    Write #1, "alpha+gamma (ver1) = " + Trim(Str(a_plus_g_1))
'    'Write #1, "alpha+gamma (ver2) = " + Trim(Str(a_plus_g_2))
'
'    Write #1, "alpha-gamma (ver1) = " + Trim(Str(a_minus_g_1))
'    'Write #1, "alpha-gamma (ver2) = " + Trim(Str(a_minus_g_2))
'
'    Write #1, "gamma-alpha (ver1) = " + Trim(Str(g_minus_a_1))
'
'    Write #1, "reco alpha (ver1) = " + Trim(Str(recAlpha1))
'    Write #1, "reco gamma (ver1) = " + Trim(Str(recGamma1))
'    Write #1, "reco alpha (ver2) = " + Trim(Str(recAlpha2))
'    Write #1, "reco gamma (ver2) = " + Trim(Str(recGamma2))
'
'    Write #1, "tg(alpha) (ver1) = " + Trim(Str(tga1))
'    Write #1, "tg(alpha) (ver2) = " + Trim(Str(tga2))
'    Write #1, "tg(gamma) (ver1) = " + Trim(Str(tgg1))
'    Write #1, "tg(gamma) (ver2) = " + Trim(Str(tgg2))
    
End Sub

Public Function myArcsin(x As Double) As Double
    If (Round(x, TOLERANCE) = 1) Then
        myArcsin = PI / 2#
    ElseIf Round(x, TOLERANCE) = -1 Then
        myArcsin = -PI / 2#
    Else
        myArcsin = Atn(x / Sqr(-x * x + 1#))
    End If
End Function

' return radians - same way as asin() of <cmath>
Public Function myAsin(sinAlpha As Double, cosAlpha As Double) As Double
  If (sinAlpha > 0#) Then
    If (cosAlpha > 0#) Then
      myAsin = myArcsin(sinAlpha)
    Else
      myAsin = PI - myArcsin(sinAlpha)
    End If
  Else
    If (cosAlpha > 0#) Then
      myAsin = 2# * PI + myArcsin(sinAlpha)
    Else
      myAsin = PI - myArcsin(sinAlpha)
    End If
  End If
End Function

Attribute VB_Name = "UserForm1"
Attribute VB_Base = "0{369DE63D-86FD-42C3-914D-9DE83A545BE2}{0D9D9685-F3C6-454C-9185-77359E15C682}"
Attribute VB_GlobalNameSpace = False
Attribute VB_Creatable = False
Attribute VB_PredeclaredId = True
Attribute VB_Exposed = False
Attribute VB_TemplateDerived = False
Attribute VB_Customizable = False
Option Explicit

Private Sub CommandButton1_Click()

    ' Open text file for debug info
    Open UserForm1.TextBox1.Text For Output As #1

    Dim i As Integer
    
    Dim prtDoc As PartDocument
    Dim prt As Part
    Dim hbds As HybridBodies
    Dim geomSet0 As HybridBody
    Dim geomSet1 As HybridBody
    Dim geomSet2 As HybridBody
    Dim geomSet3 As HybridBody
    Dim geomSetHshps1 As HybridShapes
    Dim geomSetHshps2 As HybridShapes
    Dim geomSetHshps3 As HybridShapes
    Dim fact As HybridShapeFactory
    
    Set prtDoc = CATIA.ActiveDocument
    Set prt = prtDoc.Part
    Set hbds = prt.HybridBodies
    Set geomSet0 = hbds.GetItem("Geometrical Set.0")
    Set geomSet1 = hbds.GetItem("Geometrical Set.CS1")
    Set geomSet2 = hbds.GetItem("Geometrical Set.CS2")
    Set geomSet3 = hbds.GetItem("Geometrical Set.CS3")
    Set geomSetHshps1 = geomSet1.HybridShapes
    Set geomSetHshps2 = geomSet2.HybridShapes
    Set geomSetHshps3 = geomSet3.HybridShapes
    Set fact = prt.HybridShapeFactory

    Dim M1 As New Matrix
    M1.InitBy4Points geomSetHshps1.GetItem("Point.K"), _
                     geomSetHshps1.GetItem("Point.L"), _
                     geomSetHshps1.GetItem("Point.M"), _
                     geomSetHshps1.GetItem("Point.O")
    'M1.Dump "Extracted M1"

    ' --------------------------------------------------------------
    ' Set angles
    ' --------------------------------------------------------------

    Dim startAlpha As Double
    Dim startBeta As Double
    Dim startGamma As Double
    Dim endAlpha As Double
    Dim endBeta As Double
    Dim endGamma As Double
    Dim stepAlpha As Double
    Dim stepBeta As Double
    Dim stepGamma As Double
    Dim currentAlpha As Double
    Dim currentBeta As Double
    Dim currentGamma As Double
    
    startAlpha = 60#
    startBeta = -360#
    startGamma = -360#
    endAlpha = 360#
    endBeta = 360#
    endGamma = 360#
    stepAlpha = 30#
    stepBeta = 30#
    stepGamma = 30#
    
    Dim iAlpha As Integer
    Dim iBeta As Integer
    Dim iGamma As Integer

    For iAlpha = 0 To ((endAlpha - startAlpha) / stepAlpha)
    For iBeta = 0 To ((endBeta - startBeta) / stepBeta)
    For iGamma = 0 To ((endGamma - startGamma) / stepGamma)
    
        currentAlpha = startAlpha + iAlpha * stepAlpha
        currentBeta = startBeta + iBeta * stepBeta
        currentGamma = startGamma + iGamma * stepGamma

        Call SetAngles(currentAlpha, currentBeta, currentGamma)
    
        Write #1, "Alpha=" + Trim(Str(currentAlpha)) + vbTab + _
                  "Beta =" + Trim(Str(currentBeta)) + vbTab + _
                  "Gamma=" + Trim(Str(currentGamma))

        ' --------------------------------------------------------------
        ' Read points from existing geometry and build matrices
        ' --------------------------------------------------------------
        
        Dim M2 As New Matrix
        M2.InitBy4Points geomSetHshps2.GetItem("Point.N"), _
                         geomSetHshps2.GetItem("Point.P"), _
                         geomSetHshps2.GetItem("Point.R"), _
                         geomSetHshps2.GetItem("Point.Q")
        'M2.Dump "Extracted M2"
                         
        'Dim M3 As New Matrix
        'M3.InitBy4Points geomSetHshps3.GetItem("Point.S"), _
                         geomSetHshps3.GetItem("Point.T"), _
                         geomSetHshps3.GetItem("Point.U"), _
                         geomSetHshps3.GetItem("Point.V")
        'M3.Dump "Extracted M3"
        
        ' --------------------------------------------------------------
        ' Define some known angles and translations
        ' --------------------------------------------------------------
        
        Dim alpha1 As Double
        Dim beta1 As Double
        Dim gamma1 As Double
        Dim shiftX1 As Double
        Dim shiftY1 As Double
        Dim shiftZ1 As Double
        
        alpha1 = currentAlpha ' rotation Z
        beta1 = currentBeta  ' rotation Y
        gamma1 = currentGamma ' rotation X
        shiftX1 = 3.3
        shiftY1 = 4.4
        shiftZ1 = 5.5
        
'        Dim alpha2 As Double
'        Dim beta2 As Double
'        Dim gamma2 As Double
'        Dim shiftX2 As Double
'        Dim shiftY2 As Double
'        Dim shiftZ2 As Double
'
'        alpha2 = 35# ' rotation Z
'        beta2 = 25#  ' rotation Y
'        gamma2 = 15# ' rotation X
'        shiftX2 = -6.6
'        shiftY2 = -7.7
'        shiftZ2 = -8.8
        
        ' --------------------------------------------------------------
        ' Build matrices from known angles and translations
        ' --------------------------------------------------------------
        
        Dim Mtxyz1 As New Matrix
        'Dim Mtxyz2 As New Matrix
    
        Mtxyz1.InitTXYZ alpha1, beta1, gamma1, shiftX1, shiftY1, shiftZ1
        'Mtxyz2.InitTXYZ alpha2, beta2, gamma2, shiftX2, shiftY2, shiftZ2
    
        'Dim M0 As New Matrix
        'M0.Copy M1
        'M0.Dump "M0 = M1"
        'M0.Multiply Mtxyz2
        'M0.Dump "M0 = M1*Mtxyz2"
        'M0.Multiply Mtxyz1
        'M0.Dump "M0 = M1*Mtxyz2*Mtxyz1"
        
    '    M0.ExtractAnglesAndCoordinates
        
        Dim M02 As New Matrix
        M02.Copy M1
        'M02.Dump "M02 = M1"
        M02.Multiply Mtxyz1
        'M02.Dump "M02 = M1*Mtxyz1"
        
    '    M02.ExtractAnglesAndCoordinates
        
        ' --------------------------------------------------------------
        ' Create geometry from matrix computations
        ' --------------------------------------------------------------
    
        ' Create geometry
    '    M0.CreateGeometry fact, geomSet0, "M0"
        M02.CreateGeometry fact, geomSet0, "M02"
        
        prt.Update
    
        Call QA
    
        Call CleanGS0
    
        ' --------------------------------------------------------------
        ' Extract positioning of the CS3 in the CS2 knowing the
        ' positioning of the CS2 in the CS1 and
        ' measuring the points of the CS3 in the CS1
        ' --------------------------------------------------------------
    
        ' TODO

    Next iGamma
    Next iBeta
    Next iAlpha

    ' Close output debug text file
    Close #1

    MsgBox "Done!"

End Sub

Private Sub CommandButton2_Click()
    End
End Sub

Private Sub UserForm_Initialize()
    UserForm1.TextBox1.Text = "E:\matrix1.txt"
End Sub

Private Sub SetAngles(alpha As Double, beta As Double, gamma As Double)

    Dim prtDoc As PartDocument
    Dim prt As Part
    Dim params As Parameters
    Dim paramAlpha As Parameter
    Dim paramBeta As Parameter
    Dim paramGamma As Parameter
    
    Set prtDoc = CATIA.ActiveDocument
    Set prt = prtDoc.Part
    Set params = prt.Parameters
    Set paramAlpha = params.GetItem("Geometrical Set.CS2\Rotate.Z\Angle")
    Set paramBeta = params.GetItem("Geometrical Set.CS2\Rotate.Y\Angle")
    Set paramGamma = params.GetItem("Geometrical Set.CS2\Rotate.X\Angle")
    
    paramAlpha.ValuateFromString (Trim(Str(alpha)) + "deg")
    paramBeta.ValuateFromString (Trim(Str(beta)) + "deg")
    paramGamma.ValuateFromString (Trim(Str(gamma)) + "deg")
    
    prt.Update

End Sub

Private Sub QA()

    Dim prtDoc As PartDocument
    Dim prt As Part
    Dim hbds As HybridBodies
    Dim geomSet0 As HybridBody
    Dim geomSet1 As HybridBody
    Dim geomSet2 As HybridBody
    Dim geomSet3 As HybridBody
    Dim geomSetHshps0 As HybridShapes
    Dim geomSetHshps1 As HybridShapes
    Dim geomSetHshps2 As HybridShapes
    Dim geomSetHshps3 As HybridShapes
    
    Set prtDoc = CATIA.ActiveDocument
    Set prt = prtDoc.Part
    Set hbds = prt.HybridBodies
    Set geomSet0 = hbds.GetItem("Geometrical Set.0")
    Set geomSet1 = hbds.GetItem("Geometrical Set.CS1")
    Set geomSet2 = hbds.GetItem("Geometrical Set.CS2")
    Set geomSet3 = hbds.GetItem("Geometrical Set.CS3")
    Set geomSetHshps0 = geomSet0.HybridShapes
    Set geomSetHshps1 = geomSet1.HybridShapes
    Set geomSetHshps2 = geomSet2.HybridShapes
    Set geomSetHshps3 = geomSet3.HybridShapes

    Dim recoXpoint 'As HybridShapePointCoord
    Dim recoYpoint 'As HybridShapePointCoord
    Dim recoZpoint 'As HybridShapePointCoord
    Dim recoOrigin 'As HybridShapePointCoord
    Set recoXpoint = geomSetHshps0.GetItem("Point.M02.recoX")
    Set recoYpoint = geomSetHshps0.GetItem("Point.M02.recoY")
    Set recoZpoint = geomSetHshps0.GetItem("Point.M02.recoZ")
    Set recoOrigin = geomSetHshps0.GetItem("Point.M02.recoO")

    Dim origXpoint 'As HybridShapePointCoord
    Dim origYpoint 'As HybridShapePointCoord
    Dim origZpoint 'As HybridShapePointCoord
    Dim origOrigin 'As HybridShapePointCoord
    Set origXpoint = geomSetHshps2.GetItem("Point.N")
    Set origYpoint = geomSetHshps2.GetItem("Point.P")
    Set origZpoint = geomSetHshps2.GetItem("Point.R")
    Set origOrigin = geomSetHshps2.GetItem("Point.Q")
    
    Dim coordsVarXdir(2) As Variant
    Dim coordsVarYdir(2) As Variant
    Dim coordsVarZdir(2) As Variant
    Dim coordsVarOrigin(2) As Variant
    
    Dim coordsRecoDouble(11) As Double

    recoXpoint.GetCoordinates coordsVarXdir
    recoYpoint.GetCoordinates coordsVarYdir
    recoZpoint.GetCoordinates coordsVarZdir
    recoOrigin.GetCoordinates coordsVarOrigin

    coordsRecoDouble(0) = coordsVarXdir(0) ' Xdir point - coordinate x
    coordsRecoDouble(1) = coordsVarXdir(1) ' Xdir point - coordinate y
    coordsRecoDouble(2) = coordsVarXdir(2) ' Xdir point - coordinate z
    coordsRecoDouble(3) = coordsVarYdir(0) ' Ydir point - coordinate x
    coordsRecoDouble(4) = coordsVarYdir(1) ' Ydir point - coordinate y
    coordsRecoDouble(5) = coordsVarYdir(2) ' Ydir point - coordinate z
    coordsRecoDouble(6) = coordsVarZdir(0) ' Zdir point - coordinate x
    coordsRecoDouble(7) = coordsVarZdir(1) ' Zdir point - coordinate y
    coordsRecoDouble(8) = coordsVarZdir(2) ' Zdir point - coordinate z
    coordsRecoDouble(9) = coordsVarOrigin(0) ' origin - coordinate x
    coordsRecoDouble(10) = coordsVarOrigin(1) ' origin - coordinate y
    coordsRecoDouble(11) = coordsVarOrigin(2) ' origin - coordinate z
    
    Dim coordsOrigDouble(11) As Double

    origXpoint.GetCoordinates coordsVarXdir
    origYpoint.GetCoordinates coordsVarYdir
    origZpoint.GetCoordinates coordsVarZdir
    origOrigin.GetCoordinates coordsVarOrigin

    coordsOrigDouble(0) = coordsVarXdir(0) ' Xdir point - coordinate x
    coordsOrigDouble(1) = coordsVarXdir(1) ' Xdir point - coordinate y
    coordsOrigDouble(2) = coordsVarXdir(2) ' Xdir point - coordinate z
    coordsOrigDouble(3) = coordsVarYdir(0) ' Ydir point - coordinate x
    coordsOrigDouble(4) = coordsVarYdir(1) ' Ydir point - coordinate y
    coordsOrigDouble(5) = coordsVarYdir(2) ' Ydir point - coordinate z
    coordsOrigDouble(6) = coordsVarZdir(0) ' Zdir point - coordinate x
    coordsOrigDouble(7) = coordsVarZdir(1) ' Zdir point - coordinate y
    coordsOrigDouble(8) = coordsVarZdir(2) ' Zdir point - coordinate z
    coordsOrigDouble(9) = coordsVarOrigin(0) ' origin - coordinate x
    coordsOrigDouble(10) = coordsVarOrigin(1) ' origin - coordinate y
    coordsOrigDouble(11) = coordsVarOrigin(2) ' origin - coordinate z
    
    Dim tol As Integer
    tol = 12
    
    Write #1, Trim(Str(coordsOrigDouble(0))) + vbTab + Trim(Str(coordsRecoDouble(0))) + vbTab + _
              Trim(Str(Round(coordsRecoDouble(0) - coordsOrigDouble(0), tol)))
    Write #1, Trim(Str(coordsOrigDouble(1))) + vbTab + Trim(Str(coordsRecoDouble(1))) + vbTab + _
              Trim(Str(Round(coordsRecoDouble(1) - coordsOrigDouble(1), tol)))
    Write #1, Trim(Str(coordsOrigDouble(2))) + vbTab + Trim(Str(coordsRecoDouble(2))) + vbTab + _
              Trim(Str(Round(coordsRecoDouble(2) - coordsOrigDouble(2), tol)))
    Write #1, Trim(Str(coordsOrigDouble(3))) + vbTab + Trim(Str(coordsRecoDouble(3))) + vbTab + _
              Trim(Str(Round(coordsRecoDouble(3) - coordsOrigDouble(3), tol)))
    Write #1, Trim(Str(coordsOrigDouble(4))) + vbTab + Trim(Str(coordsRecoDouble(4))) + vbTab + _
              Trim(Str(Round(coordsRecoDouble(4) - coordsOrigDouble(4), tol)))
    Write #1, Trim(Str(coordsOrigDouble(5))) + vbTab + Trim(Str(coordsRecoDouble(5))) + vbTab + _
              Trim(Str(Round(coordsRecoDouble(5) - coordsOrigDouble(5), tol)))
    Write #1, Trim(Str(coordsOrigDouble(6))) + vbTab + Trim(Str(coordsRecoDouble(6))) + vbTab + _
              Trim(Str(Round(coordsRecoDouble(6) - coordsOrigDouble(6), tol)))
    Write #1, Trim(Str(coordsOrigDouble(7))) + vbTab + Trim(Str(coordsRecoDouble(7))) + vbTab + _
              Trim(Str(Round(coordsRecoDouble(7) - coordsOrigDouble(7), tol)))
    Write #1, Trim(Str(coordsOrigDouble(8))) + vbTab + Trim(Str(coordsRecoDouble(8))) + vbTab + _
              Trim(Str(Round(coordsRecoDouble(8) - coordsOrigDouble(8), tol)))
    Write #1, Trim(Str(coordsOrigDouble(9))) + vbTab + Trim(Str(coordsRecoDouble(9))) + vbTab + _
              Trim(Str(Round(coordsRecoDouble(9) - coordsOrigDouble(9), tol)))
    Write #1, Trim(Str(coordsOrigDouble(10))) + vbTab + Trim(Str(coordsRecoDouble(10))) + vbTab + _
              Trim(Str(Round(coordsRecoDouble(10) - coordsOrigDouble(10), tol)))
    Write #1, Trim(Str(coordsOrigDouble(11))) + vbTab + Trim(Str(coordsRecoDouble(11))) + vbTab + _
              Trim(Str(Round(coordsRecoDouble(11) - coordsOrigDouble(11), tol)))
    
End Sub

Private Sub CleanGS0()

    Dim prtDoc As PartDocument
    Dim prt As Part
    Dim hbds As HybridBodies
    Dim geomSet0 As HybridBody
    Dim geomSetHshps0 As HybridShapes
    Dim sel As Selection
    
    Set prtDoc = CATIA.ActiveDocument
    Set prt = prtDoc.Part
    Set hbds = prt.HybridBodies
    Set geomSet0 = hbds.GetItem("Geometrical Set.0")
    Set geomSetHshps0 = geomSet0.HybridShapes
    Set sel = prtDoc.Selection
    
    sel.Clear
    
    Dim i As Integer
    For i = 1 To geomSetHshps0.Count
        sel.Add geomSetHshps0.Item(i)
    Next i
    
    sel.Delete
    
    prt.Update
    
End Sub

Attribute VB_Name = "matrixTests1"
Option Explicit

Sub CATMain()
    UserForm1.Show vbModeless
End Sub
